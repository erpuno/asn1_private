TS24501IES DEFINITIONS AUTOMATIC TAGS ::=
BEGIN

IMPORTS
ExtQualityOfService, MCCMNCPair, IMEI, IMEISV, TFT, TimeZoneAndTime,
GPRSTimer, GPRSTimer3, TMGI
FROM TS24008IES

APNAggMaxBitRate, EPSQualityOfService, ExtAPNAggMaxBitRate, TimeDuration
FROM TS24301IES
;


/* -- TYPE DEFINITIONS --- */

/* OpaqueData can be used for any case where the specification has
   some number of octets preceded by a 2-octet length. */
OpaqueData ::= SEQUENCE {
   --<is3GLength bitFieldSize="16"/>
   length INTEGER (1..65535),
   --<length fixed-size="0"/>
   contents OCTET STRING  
}


/* COMMON INFORMATION ELEMENTS */

/* 9.11.2.1 - Additional information */
AdditionalInfo ::= OCTET STRING

/* 9.11.2.1A - Access type */
AccessType ::= SEQUENCE {
   spare INTEGER (0..3) DEFAULT 0,
   typeOfAccess ENUMERATED {
      access3gpp(1), accessNon3gpp(2)
   }
}

/* 9.11.2.1B - DNN */
DNNList ::= SEQUENCE {
   --<is3GLength/>
   length INTEGER (1..255),
   --<length fixed-size="0"/>
   apn SEQUENCE OF IA5String
}

/* 9.11.2.2 - EAP message */
EAPMessage ::= SEQUENCE {
   --<is3GLength bitFieldSize="16"/>
   length INTEGER (1..65535),
   --<asn1typename>EAPPacketFormat</asn1typename>
   packetFormat SEQUENCE { -- defined in IETF RFC 3748, Section 4
      code EAPFormatCode,
      id INTEGER (0..255),
      length INTEGER (4..65535),
      --<length expr="@.length - 4"/>
      data OCTET STRING
   }
}

EAPFormatCode ::= ENUMERATED {
   request(1), response(2), success(3), failure(4),
   codeMax(255)
}

/* 9.11.2.6 - Intra N1 mode NAS transparent container */
IntraN1NASContainer ::= SEQUENCE {
   --<is3GLength/>
   length INTEGER (1..255),
   authCode OCTET STRING (SIZE (4)),
   cipherType INTEGER (0..15),
   integrityType INTEGER (0..15),
   spare1 INTEGER (0..7) DEFAULT 0,
   kacf BOOLEAN,
   tsc BOOLEAN,
   keysetId INTEGER (0..7),
   seqNumber INTEGER (1..255)
}

/* 9.11.2.7 - N1 mode to S1 mode NAS transparent container */
N1ToS1NASContainer ::= INTEGER (1..255)

/* 9.11.2.8 - S-NSSAI */
SNSSAI ::= SEQUENCE {
   --<is3GLength/>
   length INTEGER (1..255),
   sst SST,
   --<noPresentBit/>
   sd SD OPTIONAL,
   --<noPresentBit/>
   mappedSST OCTET STRING (SIZE (1)) OPTIONAL,
   --<noPresentBit/>
   mappedSD OCTET STRING (SIZE (3)) OPTIONAL
}

SST ::= INTEGER (1..255)

SD ::= INTEGER (1..16777215)

/* 9.11.2.9 - S1 mode to N1 mode NAS transparent container */
S1ToN1NASContainer ::= SEQUENCE {   
   --<is3GLength/>
   length INTEGER (1..255),
   authCode OCTET STRING (SIZE (4)),
   cipherType INTEGER (0..15),
   integrityType INTEGER (0..15),
   spare1 BOOLEAN DEFAULT FALSE,
   ncc INTEGER (0..7),
   tsc BOOLEAN,
   keysetId INTEGER (0..7),
   spare2 INTEGER (1..65535) DEFAULT 0
}

/* 9.11.2.10 - Service-level-AA container - added in 17.3 */
SLAAContainer ::= SEQUENCE {
   --<is3GLength bitFieldSize="16"/>
   length INTEGER (0..65535),
   --<is3GVarLenList lengthElem="length"/>
   contents SEQUENCE OF SLAAParameter
}

SLAAParameter ::= SEQUENCE {
   type SLAAParamTypes,
   --<inline/>
   param CHOICE {
      --<selector element="type" value="10"/>
      pendingInd SLAAPendingIndication,
      --<selector element="type" value="16"/>
      deviceId SLDeviceId,
      --<selector element="type" value="32"/>
      serverAddr SLAAServerAddr,
      --<selector element="type" value="48"/>
      response SLAAResponse,
      --<selector element="type" value="64"/>
      payloadType SLAAPayloadType,
      --<selector element="type" value="80"/>
      statusInd SLAAStatusIndication,
      --<selector element="type" value="112"/>
      payload SLAAPayload
   }
}

SLAAParamTypes ::= ENUMERATED {
   ptPendingInd(10), ptDeviceId(16), ptServerAddr(32), ptResponse(48),
   ptPayloadType(64), ptStatusInd(80), ptPayload(112), ptMax(255)
}

/* 9.11.2.11 - Service-level device ID - added in 17.3 */
SLDeviceId ::= SEQUENCE {
   --<is3GLength/>
   length INTEGER (1..255),
   id OCTET STRING (SIZE (1..255))
}

/* 9.11.2.12 - Service-level-AA server address - added in 17.3 */
SLAAServerAddr ::= SEQUENCE {
   --<is3GLength/>
   length INTEGER (1..255),
   addrType INTEGER (1..255),
   --<inline/>
   addr CHOICE { -- Changed in v18.10
      --<selector element="addrType" value="1"/>
      addrIpv4 OCTET STRING (SIZE (4)),
      --<selector element="addrType" value="2"/>
      addrIpv6 OCTET STRING (SIZE (16)),
      --<selector element="addrType" value="3"/>
      --<inline/>
      addrIpv4v6 SEQUENCE {
         ipv4 OCTET STRING (SIZE (4)),
         ipv6 OCTET STRING (SIZE (16))
      },
      --<selector element="addrType" value="4"/>
      --<inline/>
      addrFQDN SEQUENCE {
         length INTEGER (0..255),
         fqdn PrintableString
      }
   }
}

/* 9.11.2.13 - Service-level-AA payload - added in 17.3 */
SLAAPayload ::= SEQUENCE {
   --<is3GLength bitFieldSize="16"/>
   length INTEGER (0..65535),
   payload OCTET STRING (SIZE (1..65532))
}

/* 9.11.2.14 - Service-level-AA response - added in 17.3 */
SLAAResponse ::= SEQUENCE {
   --<is3GLength/>
   length INTEGER (1..255),
   spare INTEGER (0..15) DEFAULT 0,
   c2ar INTEGER (0..3), -- added in v17.6
   slar INTEGER (0..3) -- type modified in v17.6
}

/* 9.11.2.15 - Service-level-AA payload type - added in 17.5 */
SLAAPayloadType ::= SEQUENCE {
   --<is3GLength/>
   length INTEGER (1..255),
   type SLAAPayloadTypes
}

SLAAPayloadTypes ::= ENUMERATED {
   pltUUAA(1), pltc2Auth(2), pltMax(255)
}

/* 9.11.2.17 - Service-level-AA pending indication - added in 17.6 */
SLAAPendingIndication ::= SEQUENCE {
   spare1 INTEGER (0..15) DEFAULT 0, /* lack of 3GLength in this struct */
   spare2 INTEGER (0..7) DEFAULT 0,
   slapi BOOLEAN
}

/* 9.11.2.18 - Service-level-AA service status indication - added in 17.9 */
SLAAStatusIndication ::= SEQUENCE {
   --<is3GLength/>
   length INTEGER (1..255),
   spare INTEGER (0..127) DEFAULT 0,
   uas BOOLEAN
}


/* MOBILITY MANAGEMENT INFORMATION ELEMENTS */

/* 9.11.3.1 - MM capability */
MMCapability ::= SEQUENCE {
   --<is3GLength/>
   length INTEGER (1..255) DEFAULT 1,

   /* octet 3 */
   sgc BOOLEAN,
   hcCpCIoT BOOLEAN,
   n3Data BOOLEAN,
   cpCIoT BOOLEAN,
   restrictedEC BOOLEAN,
   lppSupported BOOLEAN,
   handoverSupported BOOLEAN,
   s1Supported BOOLEAN,
   --<noPresentBit/>
   octet4 SEQUENCE {
      racs BOOLEAN,
      nssaa BOOLEAN,
      lcs BOOLEAN,
      v2xcnpc5 BOOLEAN,
      v2xcepc5 BOOLEAN,
      v2x BOOLEAN,
      upCIoT BOOLEAN,
      srvcc BOOLEAN
   } OPTIONAL,
   --<noPresentBit/>
   octet5 SEQUENCE {
      proSel2relay BOOLEAN, -- Added in v17.3
      proSedc BOOLEAN, -- Added in v17.3
      proSedd BOOLEAN, -- Added in v17.3
      erNssai BOOLEAN,  -- Added in v17.0
      ehcCpCIoT BOOLEAN,  -- Added in v16.5
      multipleUp BOOLEAN, -- Added in v16.5
      wusa BOOLEAN,
      cag BOOLEAN
   } OPTIONAL,
   --<noPresentBit/>
   octet6 SEQUENCE { -- Added in v17.3
      pr BOOLEAN, -- Added in v17.5
      rpr BOOLEAN, -- Added in v17.5
      piv BOOLEAN, -- Added in v17.5
      ncr BOOLEAN, -- Added in v17.5
      nrpssi BOOLEAN, -- Added in v17.5
      proSel3rmt BOOLEAN,
      proSel2rmt BOOLEAN,
      proSel3relay BOOLEAN
   } OPTIONAL,
   --<noPresentBit/>
   octet7 SEQUENCE { -- Added in v17.5
      mpsiu BOOLEAN, -- Added in v18.1, renamed in v18.4
      uas BOOLEAN, -- Added in v18.1, renamed in v18.4
      nsag BOOLEAN, -- Added in v17.7
      exCag BOOLEAN, -- Added in v17.6
      sorSnpnSi BOOLEAN, -- Added in v17.6
      eventNotify BOOLEAN, -- Added in v17.6
      mint BOOLEAN,
      nssrg BOOLEAN
   } OPTIONAL,
   --<noPresentBit/>
   octet8 SEQUENCE { -- Added in v18.1
      sbts BOOLEAN, -- Added in v18.2
      nsr BOOLEAN, -- Added in v18.2
      ladnds BOOLEAN, -- Added in v18.2
      ranTiming BOOLEAN, -- Added in v18.2
      eci BOOLEAN, -- Added in v18.2
      esie BOOLEAN, -- Added in v18.2, renamed in v18.4
      rcman BOOLEAN, -- Renamed in v18.4
      rcmap BOOLEAN -- Renamed in v18.4
   } OPTIONAL,
   --<noPresentBit/>
   octet9 SEQUENCE { -- Added in v18.2
      proSel2End BOOLEAN, -- Added in v18.3, moved in v18.4
      proSel3U2URelay BOOLEAN, -- Added in v18.3, moved in v18.4
      proSel2U2URelay BOOLEAN, -- Added in v18.4
      slpspc5 BOOLEAN, -- Added in v18.4
      sbns BOOLEAN, -- Added in v18.2, moved in v18.4
      unper BOOLEAN, -- Added in v18.1, moved in v18.4
      a2xnpc5 BOOLEAN,
      a2xepc5 BOOLEAN
   } OPTIONAL,
   --<noPresentBit/>
   octet10 SEQUENCE { -- Added in v18.4
      a2xuu BOOLEAN, -- Added in v18.5
      slvi BOOLEAN,
      tempNS BOOLEAN,
      supl BOOLEAN,
      lcsupp BOOLEAN,
      pns BOOLEAN,
      rsppc5 BOOLEAN, -- Added in v18.3, moved in v18.4
      proSel3End BOOLEAN -- Added in v18.3, moved in v18.4
   } OPTIONAL,
   --<noPresentBit/>
   octet11 SEQUENCE { -- Added in v18.5
      spare INTEGER (0..15) DEFAULT 0, 
      nsuc BOOLEAN, -- Added in v18.6
      rslpl BOOLEAN, -- Added in v18.6
      nvlsatnr BOOLEAN, -- Added in v18.6
      mcsiu BOOLEAN
   } OPTIONAL,
   --<noPresentBit/>
   --<length fixed-size="0"/>
   spare OCTET STRING OPTIONAL
}

/* 9.11.3.2 - MM cause */
MMCause ::= INTEGER (0..255)

/* 9.11.3.2A - DRX parameters */
DRXParams ::= SEQUENCE {
   --<is3GLength/>
   length INTEGER (1), 
   spare INTEGER (0..15) DEFAULT 0, 
   drxValue INTEGER (0..15)
}

/* 9.11.3.3 - Identity type */
IdentityType ::= SEQUENCE {
   spare BOOLEAN DEFAULT FALSE,
   typeOfIdent TypeOfIdentity
}

TypeOfIdentity ::= ENUMERATED {
   none(0), suci(1), guti(2), imei(3), stmsi(4), imeisv(5), macAddr(6),
   eui64(7) }

/* 9.11.3.4 - 5G mobile identity */
MobileIdentity ::= CHOICE {
   none NULL,   
   suci CHOICE {
      -- The supiFormat bit in the MobileIdentity determines which of these
      -- choices is present in an encoding.
      supiImsi MobileIdentity-SUCI-IMSI,
      supiNetSpecificId MobileIdentity-SUCI-NetId
   },
   guti MobileIdentity-GUTI,
   imei IMEI,
   stmsi MobileIdentity-STMSI,
   imeisv IMEISV,
   mac MobileIdentity-MAC,
   eui-64 OCTET STRING (SIZE(8))
}

MobileIdentity-GUTI ::= SEQUENCE {
   mcc-mnc MCCMNCPair,
   amfRegionID INTEGER (0..255),
   amfSetID INTEGER (0..1023),
   amfPointer INTEGER (0..63),
   tmsi OCTET STRING (SIZE (4))
}

MobileIdentity-STMSI ::= SEQUENCE {
   amfSetID INTEGER (0..1023),
   amfPointer INTEGER (0..63),
   tmsi OCTET STRING (SIZE (4))
}

MobileIdentity-SUCI-IMSI ::= SEQUENCE {
   mcc-mnc MCCMNCPair,
   routingInd2 INTEGER (0..15),
   routingInd1 INTEGER (0..15),
   routingInd4 INTEGER (0..15),
   routingInd3 INTEGER (0..15),
   spare INTEGER (0..15) DEFAULT 0,
   protSchemeId INTEGER (0..15),
   homeNetId INTEGER (0..255),
   --<length fixed-size="0"/>
   schemeOutput OCTET STRING
}

MobileIdentity-SUCI-NetId ::= SEQUENCE {
   --<length fixed-size="0">
   nai OCTET STRING
}

MobileIdentity-MAC ::= SEQUENCE {
   mauri BOOLEAN,
   macaddr OCTET STRING (SIZE(6))
}

/* 9.11.3.5 - 5GS network feature support */
NetworkFeatureSupport ::= SEQUENCE {
   --<is3GLength/>
   length INTEGER (1..255),

   /* octet 3 */
   mpsInd BOOLEAN, 
   interNetworkWithoutN26Ind BOOLEAN,
   emfInd INTEGER (0..3), 
   emcInd INTEGER (0..3), 
   imsVoPSN3GPPInd BOOLEAN,
   imsVoPS3GPPInd BOOLEAN,

   --<noPresentBit/>
   /* octet 4 */
   octet4 SEQUENCE {
      upCIoT BOOLEAN,
      hcCpCIoT BOOLEAN,
      n3Data BOOLEAN,
      cpCIoT BOOLEAN,
      restrictedEC INTEGER (0..3),
      mcsi BOOLEAN,
      emcn3 BOOLEAN
   } OPTIONAL,

   --<noPresentBit/>
   /* octet 5 */
   octet5 SEQUENCE {
      unper BOOLEAN, -- Added in v18.1
      pr BOOLEAN, -- Added in v17.3
      rpr BOOLEAN, -- Added in v17.3
      piv BOOLEAN, -- Added in v17.3
      ncr BOOLEAN, -- Added in v17.3
      ehcCpCIoT BOOLEAN, -- Added in v16.5
      atsInd BOOLEAN,
      lcs BOOLEAN        -- Added in v16.5
   } OPTIONAL,

   --<noPresentBit/>
   /* octet 6 */
   octet6 SEQUENCE { -- Added in v18.3
      spare INTEGER (0..15) DEFAULT 0,
      rslp BOOLEAN, -- Added in v18.5
      supl BOOLEAN, -- Added in v18.4
      lcsupp BOOLEAN, -- Added in v18.4
      naps BOOLEAN
   } OPTIONAL
}

/* 9.11.3.6 - Registration result */
RegistrationResult ::= SEQUENCE {
   --<is3GLength/>
   length INTEGER (1..255),
   spare BOOLEAN DEFAULT FALSE,
   disasterRegisterValue BOOLEAN, -- Added in v17.6
   emergencyRegistered BOOLEAN,
   nssaa BOOLEAN,
   smsAllowed BOOLEAN,
   regResult INTEGER (0..7)
}

/* 9.11.3.7 - Registration type */
RegistrationType ::= SEQUENCE {
   forBit BOOLEAN,
   regisType RegistrationTypeValue
}

RegistrationTypeValue ::= ENUMERATED {
   initial(1), mobilityUpdate(2), periodicUpdate(3), emergency(4),
   snpnOnboard(5), disasterUpdate(6), disasterInitial(7)
} 

/* 9.11.3.8 - Tracking area identity */
/* Mostly the same as 24.301 except the TAC is 3 octets instead of 2... */
TrackingAreaIdent ::= SEQUENCE {
   mcc-mnc MCCMNCPair,
   tac TrackingAreaCode
}

TrackingAreaCode ::= OCTET STRING (SIZE (3))

/* 9.11.3.9 - Tracking area identity list */
/* Mostly the same as 24.301 except the TAC is 3 octets instead of 2... */
/* Also used for Service Area List type (9.11.3.49)... */
TrackingAreaIdentList ::= SEQUENCE {
   --<is3GLength/>
   length INTEGER (1..255), 
   --<is3GVarLenList lengthElem="length"/>
   idents SEQUENCE (SIZE (1..16)) OF TrackingAreaIdentListItem
}

TrackingAreaIdentListItem ::= SEQUENCE {
   allowedType BOOLEAN, -- Used by ServiceAreaList (9.11.3.49)
   typeOfList INTEGER (0..3),
   numElements INTEGER (0..31),  -- number of elements - 1
   --<inline/>
   elements CHOICE {
      --<selector element="typeOfList" value="0"/>
      --<asn1typename>PartialTrkAreaIdent0</asn1typename>
      partTrkIdentList0 SEQUENCE {
         mcc-mnc MCCMNCPair,
         --<inline/>
         --<length expr="@...numElements + 1"/>
         tacs SEQUENCE (SIZE (1..32)) OF TrackingAreaCode
      },      
      --<selector element="typeOfList" value="1"/>
      --<asn1typename>PartialTrkAreaIdent1</asn1typename>
      partTrkIdentList1 SEQUENCE {
         mcc-mnc MCCMNCPair,
         tac TrackingAreaCode
      },
      --<selector element="typeOfList" value="2"/>
      --<length expr="@.numElements + 1"/>
      --<asn1typename>PartialTrkAreaIdent2</asn1typename>
      partTrkIdentList2 SEQUENCE (SIZE (1..32)) OF TrackingAreaIdent,
      --<selector element="typeOfList" value="3"/>
      partTrkIdentList3 MCCMNCPair -- Used by ServiceAreaList (9.11.3.49)
   }
}

/* 9.11.3.9A - Update type */
UpdateType  ::= SEQUENCE {
   --<is3GLength/>
   length INTEGER (1..255),
   spare BOOLEAN DEFAULT FALSE,
   spare2 BOOLEAN DEFAULT FALSE, -- "clie" bit removed in v18.5
   epsPnbCIoT INTEGER (0..3),
   pnbCIoT INTEGER (0..3),
   ngranUpd BOOLEAN,
   smsReq BOOLEAN
}

/* 9.11.3.10 - ABBA */
ABBA ::= OCTET STRING  -- (preceeded by 1 octet length)

/* 9.11.3.12 - Additional security information */
AddlSecurityInfo ::= SEQUENCE {
   --<is3GLength/>
   length INTEGER (1..255),
   spare INTEGER (0..63) DEFAULT 0,
   rinmr BOOLEAN,
   hdp BOOLEAN
}

/* 9.11.3.12A - Additional information requested */
AdditionalInfoRequested ::= SEQUENCE {
   --<is3GLength/>
   length INTEGER (1..255),
   spare INTEGER (0..127) DEFAULT 0,
   cipherKey BOOLEAN
}

/* 9.11.3.13 - Allowed PDU session status */
AllowedPDUSessionStatus ::= SEQUENCE {
   --<is3GLength/>
   length INTEGER (1..255),
   psi-7 BOOLEAN,
   psi-6 BOOLEAN,
   psi-5 BOOLEAN,
   psi-4 BOOLEAN,
   psi-3 BOOLEAN,
   psi-2 BOOLEAN,
   psi-1 BOOLEAN,
   psi-0 BOOLEAN DEFAULT FALSE,
   psi-15 BOOLEAN,
   psi-14 BOOLEAN,
   psi-13 BOOLEAN,
   psi-12 BOOLEAN,
   psi-11 BOOLEAN,
   psi-10 BOOLEAN,
   psi-9 BOOLEAN,
   psi-8 BOOLEAN,
   --<noPresentBit/>
   spare OCTET STRING OPTIONAL
}

/* 9.11.3.18 - Configuration update indication */
ConfigUpdateIndication ::= SEQUENCE {
   spare INTEGER (0..3) DEFAULT 0,
   regRequested BOOLEAN,
   ack BOOLEAN
}

/* 9.11.3.18A - CAG information list */
CAGInfoList ::= SEQUENCE {
   --<is3GLength bitFieldSize="16"/>
   length INTEGER (0..65535),
   --<is3GVarLenList lengthElem="length"/>
   --<noPresentBit/>
   entries SEQUENCE OF CAGEntry OPTIONAL
}

CAGEntry ::= SEQUENCE {
   length INTEGER (1..255),
   mcc-mnc MCCMNCPair,
   spare INTEGER (0..127) DEFAULT 0,
   cagOnly BOOLEAN,
   --<noPresentBit/>
   --<length fixed-size="0"/>
   cagID OCTET STRING OPTIONAL
}

/* 9.11.3.18B - CIoT small data container */
CIoTSmallDataContainer ::= SEQUENCE {
   --<is3GLength/>
   length INTEGER (1..255),
   --<is3GVarLenList lengthElem="length"/>
   --<storage>array</storage>
   dataType CIoTDataTypes,
   --<inline/>
   containerContents CHOICE {
      --<selector element="dataType" value="0"/>
      ctrlPlaneUserData SEQUENCE {
         ddx INTEGER (0..3),
         pduSessionId INTEGER (0..7)
      },
      --<selector element="dataType" value="1"/>
      sms SEQUENCE {
         spare INTEGER (0..31) DEFAULT 0
      },
      --<selector element="dataType" value="2"/>
      locSvcsMsgContainer SEQUENCE {
         ddx INTEGER (0..3),
         spare INTEGER (0..7) DEFAULT 0,
         addlInfoLen INTEGER (0..255),
         --<noPresentBit/>
         --<length expr="@.addlInfoLen"/>
         addlInfo OCTET STRING OPTIONAL
      }
   },
   --<length fixed-size="0"/>
   contents OCTET STRING
}

CIoTDataTypes ::= ENUMERATED {
   ciotCtrlPlaneUserData(0), ciotSMS(1), ciotLocSvcsMsg(2), ciotMAX(7)
} 

/* 9.11.3.18C - Ciphering key data */
CipheringKeyData ::= SEQUENCE {
   --<is3GLength bitFieldSize="16"/>
   length INTEGER (1..65535),
   --<is3GVarLenList lengthElem="length"/>
   dataSet SEQUENCE OF CipherDataSet
}

CipherDataSet ::= SEQUENCE {
   cipherId INTEGER (0..65535),
   cipherKey OCTET STRING (SIZE (16)),
   spare1 INTEGER (0..7) DEFAULT 0,
   c0Len INTEGER (0..31),
   --<length expr="@c0Len"/>
   c0 OCTET STRING,
   spare2 INTEGER (0..15) DEFAULT 0,
   eutraPosSIB SEQUENCE {
      --<is3GLength bitFieldSize="4"/>
      length INTEGER (0..15),
      --<noPresentBit/>
      octet1 SEQUENCE {
         posSIBType1-1 BOOLEAN,
         posSIBType1-2 BOOLEAN,
         posSIBType1-3 BOOLEAN,
         posSIBType1-4 BOOLEAN,
         posSIBType1-5 BOOLEAN,
         posSIBType1-6 BOOLEAN,
         posSIBType1-7 BOOLEAN,
         posSIBType1-8 BOOLEAN
      } OPTIONAL,
      --<noPresentBit/>
      octet2 SEQUENCE {
         posSIBType2-1 BOOLEAN,
         posSIBType2-2 BOOLEAN,
         posSIBType2-3 BOOLEAN,
         posSIBType2-4 BOOLEAN,
         posSIBType2-5 BOOLEAN,
         posSIBType2-6 BOOLEAN,
         posSIBType2-7 BOOLEAN,
         posSIBType2-8 BOOLEAN
      } OPTIONAL,
      --<noPresentBit/>
      octet3 SEQUENCE {
         posSIBType2-9 BOOLEAN,
         posSIBType2-10 BOOLEAN,
         posSIBType2-11 BOOLEAN,
         posSIBType2-12 BOOLEAN,
         posSIBType2-13 BOOLEAN,
         posSIBType2-14 BOOLEAN,
         posSIBType2-15 BOOLEAN,
         posSIBType2-16 BOOLEAN
      } OPTIONAL,
      --<noPresentBit/>
      octet4 SEQUENCE {
         posSIBType2-17 BOOLEAN,
         posSIBType2-18 BOOLEAN,
         posSIBType2-19 BOOLEAN,
         posSIBType2-20 BOOLEAN,
         posSIBType2-21 BOOLEAN,
         posSIBType2-22 BOOLEAN,
         posSIBType2-23 BOOLEAN,
         posSIBType2-24 BOOLEAN
      } OPTIONAL,
      --<noPresentBit/>
      octet5 SEQUENCE {
         posSIBType2-25 BOOLEAN,
         posSIBType3-1 BOOLEAN,
         posSIBType4-1 BOOLEAN,
         posSIBType5-1 BOOLEAN,
         posSIBType1-9 BOOLEAN, -- added in v17.13
         posSIBType1-10e BOOLEAN, -- added in v17.13
         spare INTEGER(0..3) DEFAULT 0
      } OPTIONAL
   },
   spare3 INTEGER (0..15) DEFAULT 0,
   nrPosSIB SEQUENCE {
      --<is3GLength bitFieldSize="4"/>
      length INTEGER (0..15),
      --<noPresentBit/>
      octet1 SEQUENCE {
         posSIBType1-1 BOOLEAN,
         posSIBType1-2 BOOLEAN,
         posSIBType1-3 BOOLEAN,
         posSIBType1-4 BOOLEAN,
         posSIBType1-5 BOOLEAN,
         posSIBType1-6 BOOLEAN,
         posSIBType1-7 BOOLEAN,
         posSIBType1-8 BOOLEAN
      } OPTIONAL,
      --<noPresentBit/>
      octet2 SEQUENCE {
         posSIBType2-1 BOOLEAN,
         posSIBType2-2 BOOLEAN,
         posSIBType2-3 BOOLEAN,
         posSIBType2-4 BOOLEAN,
         posSIBType2-5 BOOLEAN,
         posSIBType2-6 BOOLEAN,
         posSIBType2-7 BOOLEAN,
         posSIBType2-8 BOOLEAN
      } OPTIONAL,
      --<noPresentBit/>
      octet3 SEQUENCE {
         posSIBType2-9 BOOLEAN,
         posSIBType2-10 BOOLEAN,
         posSIBType2-11 BOOLEAN,
         posSIBType2-12 BOOLEAN,
         posSIBType2-13 BOOLEAN,
         posSIBType2-14 BOOLEAN,
         posSIBType2-15 BOOLEAN,
         posSIBType2-16 BOOLEAN
      } OPTIONAL,
      --<noPresentBit/>
      octet4 SEQUENCE {
         posSIBType2-17 BOOLEAN,
         posSIBType2-18 BOOLEAN,
         posSIBType2-19 BOOLEAN,
         posSIBType2-20 BOOLEAN,
         posSIBType2-21 BOOLEAN,
         posSIBType2-22 BOOLEAN,
         posSIBType2-23 BOOLEAN,
         posSIBType3-1 BOOLEAN
      } OPTIONAL,
      --<noPresentBit/>
      octet5 SEQUENCE {
         posSIBType4-1 BOOLEAN,
         posSIBType5-1 BOOLEAN,
         posSIBType6-1 BOOLEAN,
         posSIBType6-2 BOOLEAN,
         posSIBType6-3 BOOLEAN,
         posSIBType6-4 BOOLEAN, -- added in v17.13
         posSIBType6-5 BOOLEAN, -- added in v17.13
         posSIBType6-6 BOOLEAN -- added in v17.13
      } OPTIONAL,
      --<noPresentBit/>
      octet6 SEQUENCE { -- added in v17.13
         posSIBType1-9 BOOLEAN,
         posSIBType1-10 BOOLEAN,
         posSIBType2-24 BOOLEAN,
         posSIBType2-25 BOOLEAN,
         spare INTEGER(0..15) DEFAULT 0      
      } OPTIONAL
   },

   validityStartTime TimeZoneAndTime,
   validityDuration INTEGER (0..65535),
   taiList TrackingAreaIdentList
}

/* 9.11.3.18D - Control plane service type */
ControlPlaneServiceType ::= SEQUENCE {
   spare BOOLEAN DEFAULT FALSE,
   value INTEGER (0..7)
}

/* 9.11.3.20 - Deregistration type */
DeregistrationType ::= SEQUENCE {
   switchOff BOOLEAN,
   reregReqd BOOLEAN,
   accessType INTEGER (0..3)
}

/* 9.11.3.24 - EPS NAS message container */
EPSMessageContainer ::= SEQUENCE {
   --<is3GLength bitFieldSize="16"/>
   length INTEGER (1..65535),
   --<length fixed-size="0"/>
   contents OCTET STRING
}

/* 9.11.3.29 - LADN Indication */
LADNIndication ::= SEQUENCE {
   --<is3GLength bitFieldSize="16"/>
   length INTEGER (0..65535),
   --<is3GVarLenList lengthElem="length"/>
   --<noPresentBit/>
   contents SEQUENCE OF DNNList OPTIONAL
}

/* 9.11.3.30 - LADN */
LADNList ::= SEQUENCE {
   --<is3GLength bitFieldSize="16"/>
   length INTEGER (0..65535),
   --<is3GVarLenList lengthElem="length"/>
   contents SEQUENCE OF LADN
}

LADN ::= SEQUENCE {
   dnn DNNList,
   tai TrackingAreaIdent
}

/* 9.11.3.31 - MICO indication */
MICOIndication ::= SEQUENCE {
   spare INTEGER (0..3) DEFAULT 0,
   sprti BOOLEAN,
   raai BOOLEAN
}

/* 9.11.3.31A - MA PDU session information */
MAPDUSessionInfo ::= ENUMERATED {   
   noAddlInfo(0), networkUpgAllowed(1), mapduMAX(15)
}

/* 9.11.3.31B - Mapped NSSAI */
MappedNSSAI ::= SEQUENCE {
   --<is3GLength/>
   length INTEGER (1..255),
   --<is3GVarLenList lengthElem="length"/>
   contents SEQUENCE (SIZE (1..8)) OF MappedSNSSAIContent
}

MappedSNSSAIContent ::= SEQUENCE {
   --<is3GLength/>
   length INTEGER (1..255),
   mappedSST OCTET STRING (SIZE (1)),
   --<noPresentBit/>
   mappedSD OCTET STRING (SIZE (3)) OPTIONAL
}

/* 9.11.3.32 - NAS key set identifier */
/* Defined in TS24301IEs.asn */

/* 9.11.3.33 - NAS message container */
/* Different from NASMessageContainer defined in 24.301... */
NASMessageContainer2 ::= SEQUENCE {
   --<is3GLength bitFieldSize="16"/>
   length INTEGER (1..65535),
   --<length fixed-size="0"/>
   contents OCTET STRING (SIZE (1..65535))
} 

/* 9.11.3.34 - NAS security algorithms */
NASSecurityAlgorithm ::= SEQUENCE {
   cipherType CipherTypes,
   protectionType ProtectionTypes
}

CipherTypes ::= ENUMERATED {
   ia0(0), ia1(1), ia2(2), ia3(3), ia4(4), ia5(5), ia6(6), ia7(7),
   cipherTypeMAX(15)
}

ProtectionTypes ::= ENUMERATED {
   ea0(0), ea1(1), ea2(2), ea3(3), ea4(4), ea5(5), ea6(6), ea7(7),
   protectionTypeMAX(15)
}

/* 9.11.3.36 - Network slicing indication */
NetSliceIndication ::= SEQUENCE {
   spare INTEGER (0..3) DEFAULT 0,
   dcni BOOLEAN,
   nssci BOOLEAN
}

/* 9.11.3.37 - NSSAI */
NSSAI ::= SEQUENCE {
   --<is3GLength/>
   length INTEGER (1..255),
   --<is3GVarLenList lengthElem="length"/>
   contents SEQUENCE (SIZE (1..16)) OF SNSSAI
}

/* 9.11.3.37A - NSSAI inclusion mode */
NSSAIInclusionMode ::= SEQUENCE {
   spare INTEGER (0..3) DEFAULT 0,
   inclusionMode ENUMERATED {
      modeA(0), modeB(1), modeC(2), modeD(3)
   }
}

/* 9.11.3.38 - Operator defined access category definitions */
AccessCategoryDefinitions ::= SEQUENCE {
   --<is3GLength bitFieldSize="16"/>
   length INTEGER (1..65535),
   --<is3GVarLenList lengthElem="length"/>
   --<noPresentBit/>
   contents SEQUENCE OF AccessCategoryDefinition OPTIONAL
}

AccessCategoryDefinition ::= SEQUENCE {
   precedence INTEGER (1..255),
   psac BOOLEAN,
   spare INTEGER (0..3) DEFAULT 0,
   categoryNum INTEGER (0..31),
   --<is3GLength/>
   length INTEGER (1..255),
   --<is3GVarLenList lengthElem="length"/>
   criteria SEQUENCE OF Criteria, -- Changed in v18.10
   --<noPresentBit/>
   categories SEQUENCE {
      spare2 INTEGER (0..7) DEFAULT 0,
      accessCategory AccessCategories
   } OPTIONAL
}

Criteria ::= SEQUENCE { -- Added in v18.10
   type INTEGER (0..255),
   count INTEGER (1..255),
   --<inline/>
   value CHOICE {
      --<selector element="type" value="0"/>
      --<length expr="@count"/>
      dnn SEQUENCE OF DNNList,
      --<selector element="type" value="1"/>
      --<length expr="@count"/>
      osId SEQUENCE OF OSIds,
      --<selector element="type" value="2"/>
      --<length expr="@count"/>
      snssai SEQUENCE OF SNSSAI
   }
}

OSIds ::= SEQUENCE {
   osId OCTET STRING (SIZE (16)),
   osAppId LenWithOctStrVal
}

AccessCategories ::= ENUMERATED {
   category0(0), category1(1), category2(2), category3(3), category4(4),
   category5(5), category6(6), category7(7), category9(9), category10(10),
   categoryMAX(31)
}

/* 9.11.3.39 - Payload container
   Warning: this type covers the specific case where the payload container
   type is 15 (Multiple payloads).
*/
MultiPayloadContainer ::= SEQUENCE {
   --<is3GLength bitFieldSize="16"/>
   length INTEGER (1..65535),
   contents PayloadContainerContents
} 

PayloadContainerContents ::= SEQUENCE {
   numEntries INTEGER (0..255),
   --<inline/>
   --<length expr="@numEntries"/>
   entries SEQUENCE (SIZE (0..255)) OF PayloadContainerEntry
}

PayloadContainerEntry ::= SEQUENCE {
   entryLength INTEGER (1..65535),
   numOptIEs INTEGER (1..15),
   type PayloadContainerType,
   --<inline/>
   --<length expr="@numOptIEs"/>
   optionalIEs SEQUENCE (SIZE (1..15)) OF OptionalIE,
   contents OCTET STRING (SIZE (0..65535))
}

OptionalIE ::= SEQUENCE {
   type INTEGER (0..255),
   value OCTET STRING   -- (preceeded by 1 octet length)
}

-- Corresponds to "eventNotify" container type below...
EventNotification ::= SEQUENCE {
   numIndicators INTEGER (0..255),
   --<inline/>
   --<length expr="@numIndicators"/>
   indicators SEQUENCE OF EventIndicator
}

EventIndicator ::= SEQUENCE {
   type INTEGER (1..255),
   length INTEGER (1..255),
   --<length fixed-size="0"/>
   value OCTET STRING
}

-- Corresponds to "uppCmi" container type below...
UppCmi ::= SEQUENCE {
   messageType INTEGER (0..255),
   --<noPresentBit/>
   messagePayload OCTET STRING (SIZE (0..257)) OPTIONAL
}

/* 9.11.3.40 - Payload container type */
PayloadContainerType ::= ENUMERATED {
   n1SmInfo(1), sms(2), lppMessage(3), transparent(4), uePolicy(5),
   ueParams(6), locSvcs(7), ciotUserData(8), svcLvlAA(9), eventNotify(10),
   uppCmi(11), slpp(12), multPayloads(15)
}

/* 9.11.3.41 - PDU session identity 2 */
PDUSessionId2 ::= INTEGER (0..255)

/* 9.11.3.42 - PDU session reactivation result */
SessionReactivateRslt ::= SEQUENCE {
   --<is3GLength/>
   length INTEGER (1..255),
   psi-7 BOOLEAN,
   psi-6 BOOLEAN,
   psi-5 BOOLEAN,
   psi-4 BOOLEAN,
   psi-3 BOOLEAN,
   psi-2 BOOLEAN,
   psi-1 BOOLEAN,
   psi-0 BOOLEAN DEFAULT FALSE,
   psi-15 BOOLEAN,
   psi-14 BOOLEAN,
   psi-13 BOOLEAN,
   psi-12 BOOLEAN,
   psi-11 BOOLEAN,
   psi-10 BOOLEAN,
   psi-9 BOOLEAN,
   psi-8 BOOLEAN,   
   --<length fixed-size="0"/>
   --<noPresentBit/>
   spare OCTET STRING OPTIONAL
}

/* 9.11.3.43 - PDU session reactivation result error cause */
SessionReactivateCause ::= SEQUENCE {
   --<is3GLength bitFieldSize="16"/>
   length INTEGER (1..512),
   --<is3GVarLenList lengthElem="length"/>
   reactivateCause SEQUENCE (SIZE (1..255)) OF ReactivateCause
}

ReactivateCause ::= SEQUENCE {
   sessionId INTEGER (0..255),
   cause MMCause
}

/* 9.11.3.44 - PDU session status */
PDUSessionStatus ::= SessionReactivateRslt

/* 9.11.3.46 - Rejected NSSAI */
RejectedNSSAIList ::= SEQUENCE {
   --<is3GLength/>
   length INTEGER (1..255),
   --<is3GVarLenList lengthElem="length"/>
   rejectedNSSAI SEQUENCE (SIZE (1..8)) OF RejectedNSSAI
}

RejectedNSSAI ::= SEQUENCE {
   length INTEGER (1..15),
   cause  ENUMERATED { unavailInCurrPlmn(0), unavailInCurrRegisArea(1),
                       authPending(2), causeMAX(15) },
   sst SST,
   --<noPresentBit/>
   sd SD OPTIONAL
}

/* 9.11.3.47 - Request type */
RequestType ::= SEQUENCE {
   spare BOOLEAN DEFAULT FALSE,
   reqType RequestTypes
}

RequestTypes ::= ENUMERATED {
 initialReq(1), existPduSession(2), initialEmerReq(3), emerPduSession(4),
 modifyReq(5), maPduReq(6), reqTypeMAX(7)
}

/* 9.11.3.49 - Service Area List */
/* Same as 9.11.3.9 (Tracking area identity list) */

/* 9.11.3.50 - Service type */
ServiceType ::= ENUMERATED {
   signaling(0), data(1), mobTermSvc(2), emerSvc(3), emerSvcFallback(4),
   hiPriAccess(5), elevSignal(6), serviceTypeMAX(15)
}

/* 9.11.3.50A - SMS indication */
SMSIndication ::= SEQUENCE {
   spare INTEGER (0..7) DEFAULT 0,
   sai BOOLEAN
}

/* 9.11.3.51 - SOR transparent container */

/* This IE requires custom decoding due to the lowest bit in the header octet
   determining whether the IE contains steering or ack of steering information.
*/
SORTransparentContainer ::= SEQUENCE {
   --<is3GLength bitFieldSize="16"/>
   length INTEGER (0..65535),
   steeringOrAck CHOICE {
      steering SORSteering,
      ack SORAck
   }
}

/* SOR for data type = 0 (steering of roaming information) */
SORSteering ::= SEQUENCE {
   /* Header - Figure 5 */
   spare INTEGER (0..7) DEFAULT 0,
   ap INTEGER (0..1),
   ack BOOLEAN,
   listType INTEGER(0..1),
   listInd BOOLEAN,
   dataType INTEGER(0..1) DEFAULT 0,   /* always 0 */

   sorMAC OCTET STRING (SIZE (16)),
   counter OCTET STRING (SIZE (2)),
   --<inline/>
   --<noPresentBit/>
   content CHOICE {
      --<selector element="listType" value="0"/>      
      --<length fixed-size="0"/>
      securedPacket OCTET STRING,
      --<selector element="listType" value="1"/>    
      --<inline/>
      plmnInfo CHOICE {
         --<selector element="@ap" value="0"/>      
         --<length fixed-size="0"/>
         plmnIds SEQUENCE OF PLMNTechIDs,
         --<selector element="@ap" value="1"/>      
         plmnList PLMNTechList
      }
   } OPTIONAL
}

PLMNTechList ::= SEQUENCE {
   length INTEGER (0..255),
   --<is3GVarLenList lengthElem="length"/>
   plmnIds SEQUENCE OF PLMNTechIDs,
   addlParams AdditionalParams
}

PLMNTechIDs ::= SEQUENCE {
    id OCTET STRING (SIZE(3)),
    techId OCTET STRING (SIZE(2))
}

AdditionalParams ::= SEQUENCE {
   spare INTEGER (0..15) DEFAULT 0,
   sssli INTEGER (0..1), -- added in v18.4
   sssi INTEGER (0..1),
   sscmi BOOLEAN,
   si INTEGER (0..1),
   --<inline/>
   sorCmci CHOICE {
      --<selector element="si" value="0"/>
      absent NULL,
      --<selector element="si" value="1"/>
      cmcis CMCIList
   },
   --<inline/>
   sorSnpnSi CHOICE {
      --<selector element="sssi" value="0"/>
      absent NULL,
      --<selector element="sssi" value="1"/>
      snpnsi SNPNSI
   },
   --<inline/>
   sorSnpnSiLs CHOICE { -- added in v18.4
      --<selector element="sssli" value="0"/>
      absent NULL,
      --<selector element="sssli" value="1"/>
      snpnsils SNPNSILS
   }
}

CMCIList ::= SEQUENCE {
   --<is3GLength bitFieldSize="16"/>
   length INTEGER (0..65535),
   --<is3GVarLenList lengthElem="length"/>
   cmciRules SEQUENCE OF CMCIRules
}

CMCIRules ::= SEQUENCE {
   --<is3GLength bitFieldSize="16"/>
   length INTEGER (0..65535),
   tsorCmTimer GPRSTimer,
   type INTEGER (0..255),  
   --<inline/>
   value CHOICE {
      --<selector element="type" value="1"/>
      dnn DNNList,
      --<selector element="type" value="2"/>
      sst SST,
      --<selector element="type" value="3"/>
      --<inline/>
      sstSd SEQUENCE {
         sst SST,
         sd SD
      },
      --<selector element="type" value="4"/>
      imsRegis NULL,
      --<selector element="type" value="5"/>
      mmtelVoice NULL,
      --<selector element="type" value="6"/>
      mmtelVideo NULL,
      --<selector element="type" value="7"/>
      sms NULL,
      --<selector element="type" value="8"/>
      sor NULL,
      --<selector element="type" value="255"/>
      matchAll NULL
   }
}

SNPNSI ::= SEQUENCE {
   --<is3GLength bitFieldSize="16"/>
   length INTEGER (0..65535),
   spare INTEGER (0..63) DEFAULT 0,
   clgi INTEGER (0..1),
   clsi INTEGER (0..1),
   --<inline/>
   snpnList CHOICE {
      --<selector element="clsi" value="0"/>
      absent NULL,
      --<selector element="clsi" value="1"/>
      snpns SNPNList2
   },
   --<inline/>
   ginList CHOICE {
      --<selector element="clgi" value="0"/>
      absent NULL,
      --<selector element="clgi" value="1"/>
      gins GINList
   }
}

/* The SNPN list here is very similar to SNPNList (9.11.3.92), but the
   fields are laid out slightly different, so a new structure is needed
   here... */
SNPNList2 ::= SEQUENCE {
   --<is3GLength bitFieldSize="16"/>
   length INTEGER (0..65535),
   --<is3GVarLenList lengthElem="length"/>
   snpnIds SEQUENCE OF SNPNIdentity
}

SNPNIdentity ::= SEQUENCE {
   mcc-mnc MCCMNCPair,
   spare INTEGER (0..15) DEFAULT 0,
   assignMode INTEGER (0..15),
   nidDigit2 INTEGER (0..15),
   nidDigit1 INTEGER (0..15),
   nidDigit4 INTEGER (0..15),
   nidDigit3 INTEGER (0..15),
   nidDigit6 INTEGER (0..15),
   nidDigit5 INTEGER (0..15),
   nidDigit8 INTEGER (0..15),
   nidDigit7 INTEGER (0..15),
   nidDigit10 INTEGER (0..15),
   nidDigit9 INTEGER (0..15)
}

GINList ::= SEQUENCE {
   --<is3GLength bitFieldSize="16"/>
   length INTEGER (0..65535),
   --<is3GVarLenList lengthElem="length"/>
   gins SEQUENCE OF GIN
}

/* The GIN structure (at least since v18.2) is the same as SNPNIdentity... */
GIN ::= SNPNIdentity

SNPNSILS ::= SEQUENCE { -- added in v18.4
   --<is3GLength bitFieldSize="16"/>
   length INTEGER (0..65535),
   spare INTEGER (0..63) DEFAULT 0,
   clglsi INTEGER (0..1),
   clslsi INTEGER (0..1),
   --<inline/>
   localSnpnList CHOICE {
      --<selector element="clslsi" value="0"/>
      absent NULL,
      --<selector element="clslsi" value="1"/>
      localSnpns LocalizedSNPNList
   },
   --<inline/>
   localGinList CHOICE {
      --<selector element="clglsi" value="0"/>
      absent NULL,
      --<selector element="clglsi" value="1"/>
      localGins LocalizedGINList
   }
}

LocalizedSNPNList ::= SEQUENCE {
   --<is3GLength bitFieldSize="16"/>
   length INTEGER (0..65535),
   --<is3GVarLenList lengthElem="length"/>
   snpnInfo SEQUENCE OF LocalizedSNPNInfo
}

LocalizedSNPNInfo ::= SEQUENCE {
   --<is3GLength bitFieldSize="16"/>
   length INTEGER (0..65535),
   spare INTEGER (0..31) DEFAULT 0,
   lvii INTEGER (0..1), -- added in v18.5
   laii INTEGER (0..1), -- added in v18.4
   timeInd INTEGER (0..1),
   --<noPresentBit/>
   snpnId SNPNIdentity OPTIONAL,
   --<inline/>
   timeValidity CHOICE { -- added in v18.4
      --<selector element="timeInd" value="0"/>
      absent NULL,
      --<selector element="timeInd" value="1"/>
      info TimePeriodInfo
   },
   --<inline/>
   locationAssistance CHOICE { -- added in v18.4
      --<selector element="laii" value="0"/>
      absent NULL,
      --<selector element="laii" value="1"/>
      info LocationAssistanceInfo
   },
   --<inline/>
   locationValidity CHOICE { -- added in v18.5
      --<selector element="lvii" value="0"/>
      absent NULL,
      --<selector element="lvii" value="1"/>
      info LocationValidityInformation
   }
}

TimePeriodInfo ::= SEQUENCE {
   numPeriods INTEGER (1..255),
   --<inline/>
   --<length expr="@numPeriods"/>
   periods SEQUENCE OF TimePeriod
}

TimePeriod ::= SEQUENCE {
   startTime SEQUENCE {
      seconds INTEGER (0..4294967295),
      fraction INTEGER (0..4294967295)
   },
   stopTime SEQUENCE {
      seconds INTEGER (0..4294967295),
      fraction INTEGER (0..4294967295)
   }
}

LocationAssistanceInfo ::= SEQUENCE { -- Modified in v18.5
   spare INTEGER (0..31) DEFAULT 0,
   taisi INTEGER (0..1),
   taipi INTEGER (0..1),
   gadi INTEGER (0..1),
   --<inline/>
   geoAreaDescs CHOICE {
      --<selector element="gadi" value="0"/>
      absent NULL,
      --<selector element="gadi" value="1"/>
      present GeoAreaDescription
   },
   --<inline/>
   plmnTAI CHOICE {
      --<selector element="taipi" value="0"/>
      absent NULL,
      --<selector element="taipi" value="1"/>
      present PLMNTrackingAreaInfoList
   },
   --<inline/>
   snpnTAI CHOICE {
      --<selector element="taisi" value="0"/>
      absent NULL,
      --<selector element="taisi" value="1"/>
      present SNPNTrackingAreaInfoList
   }
}

GeoAreaDescription ::= SEQUENCE {
   numDescriptions INTEGER (1..255),
   --<inline/>
   --<length expr="@numDescriptions"/>
   descriptions SEQUENCE OF AreaDescriptions
}

AreaDescriptions ::= SEQUENCE {
   shapeType INTEGER (0..255),
   shapeDesc OCTET STRING (SIZE (7..105))
}

PLMNTrackingAreaInfoList ::= SEQUENCE {
   numPlmns INTEGER (1..255),
   --<inline/>
   --<length expr="@numPlmns"/>
   descriptions SEQUENCE OF PLMNTrackingAreaInfo
}

PLMNTrackingAreaInfo ::= SEQUENCE {
   mcc-mnc MCCMNCPair,
   tacList TrackingAreaCodeList
}

TrackingAreaCodeList  ::= SEQUENCE {
   numTacs INTEGER (1..255),
   --<inline/>
   --<length expr="@numTacs"/>
   tacs SEQUENCE OF TrackingAreaCode
}

SNPNTrackingAreaInfoList ::= SEQUENCE {
   numSnpns INTEGER (1..255),
   --<inline/>
   --<length expr="@numSnpns"/>
   descriptions SEQUENCE OF SNPNTrackingAreaInfo
}

SNPNTrackingAreaInfo ::= SEQUENCE {
   snpnId SNPNIdentity,
   tacList TrackingAreaCodeList
}

/* LocationValidityInfo already in use... */
LocationValidityInformation ::= SEQUENCE { -- Added in v18.5
   spare INTEGER (0..127) DEFAULT 0,
   taci INTEGER (0..1),
   --<inline/>
   tacList CHOICE {
      --<selector element="taci" value="0"/>
      absent NULL,
      --<selector element="taci" value="1"/>
      present TrackingAreaCodeList
   }
}

LocalizedGINList ::= SEQUENCE {
   --<is3GLength bitFieldSize="16"/>
   length INTEGER (0..65535),
   --<is3GVarLenList lengthElem="length"/>
   ginInfo SEQUENCE OF LocalizedGINInfo
}

/* The localized GINInfo structure (at least since v18.2) is the same as
   localized SNPNInfo... */
LocalizedGINInfo ::= LocalizedSNPNInfo

/* SOR for data type = 1 (ack of steering of roaming information) */
SORAck ::= SEQUENCE {
   /* Header - Figure 6 */
   spare INTEGER (0..15) DEFAULT 0,
   mssnpnsils BOOLEAN, -- Added in v18.2
   mssnpnsi BOOLEAN, -- Added in v17.7
   mssi BOOLEAN,
   dataType INTEGER(0..1) DEFAULT 1,   /* always 1 */

   sorMAC OCTET STRING(SIZE(16))
}

/* 9.11.3.53A - UE Parameters Update Transparent Container */

/* This IE requires custom decoding due to the lowest bit in the header octet
   determining whether the IE contains an update list or ack of an update list.
*/   
UEParamUpdateContainer ::= SEQUENCE {
   --<is3GLength bitFieldSize="16"/>
   length INTEGER (0..65535),
   updateOrAck CHOICE {
      update UEParamUpdate,
      ack UEParamUpdateAck
   }
}

/* UE Param Update for data type = 0 (UE parameters update list) */
UEParamUpdate ::= SEQUENCE {
   /* Header - Figure 6 */
   spare INTEGER (0..31) DEFAULT 0,
   reg BOOLEAN,
   ack BOOLEAN,
   dataType INTEGER(0..1) DEFAULT 0, /* always 0 */

   mac OCTET STRING (SIZE(16)),
   counter OCTET STRING (SIZE(2)),
   --<length fixed-size="0"/>
   updateList SEQUENCE OF UEParamUpdateDataSet
}

UEParamUpdateDataSet ::= SEQUENCE {
   spare INTEGER (0..15),
   dataSetType INTEGER(0..15),
   dataSetLen INTEGER(0..65535),
   --<inline/>
   dataSet CHOICE {
      --<selector element="dataSetType" value="1"/>      
      --<length expr="@dataSetLen"/>
      securedPacket OCTET STRING,
      --<selector element="dataSetType" value="2"/>      
      --<length expr="@dataSetLen"/>
      defCfgNSSAI SNSSAI,
      --<selector element="dataSetType" value="3"/>      
      --<length expr="@dataSetLen"/>
      --<inline/>
      disasterRoaming SEQUENCE { -- Added in v17.5
         spare INTEGER (0..63),
         aol BOOLEAN,
         drei BOOLEAN
      },
      --<selector element="dataSetType" value="4"/>      
      --<length expr="@dataSetLen"/>
      --<inline/>
      routingIndicator SEQUENCE { -- Added in v17.6
         routingInd2 INTEGER (0..15),
         routingInd1 INTEGER (0..15),
         routingInd4 INTEGER (0..15),
         routingInd3 INTEGER (0..15)
      }
   }
}

/* UE Param Update for data type = 1 (UE parameters update list acknowledgement)
*/
UEParamUpdateAck ::= SEQUENCE {
   /* Header - Figure 7 */
   spare INTEGER (0..127) DEFAULT 0,
   dataType INTEGER(0..1) DEFAULT 1, /* always 1 */

   mac OCTET STRING (SIZE(16))
}

/* 9.11.3.54 - UE security capability */
UESecurityCapability ::= SEQUENCE {
   --<is3GLength/>
   length INTEGER (0..255),

   /* octet 3 */
   ea0 BOOLEAN,
   ea1 BOOLEAN,
   ea2 BOOLEAN,
   ea3 BOOLEAN,
   ea4 BOOLEAN,
   ea5 BOOLEAN,
   ea6 BOOLEAN,
   ea7 BOOLEAN,

   /* octet 4 */
   ia0 BOOLEAN,
   ia1 BOOLEAN,
   ia2 BOOLEAN,
   ia3 BOOLEAN,
   ia4 BOOLEAN,
   ia5 BOOLEAN,
   ia6 BOOLEAN,
   ia7 BOOLEAN,

   /* octet 5 */
   --<noPresentBit/>
   octet5 SEQUENCE {
      eea0 BOOLEAN,
      eea1 BOOLEAN,
      eea2 BOOLEAN,
      eea3 BOOLEAN,
      eea4 BOOLEAN,
      eea5 BOOLEAN,
      eea6 BOOLEAN,
      eea7 BOOLEAN
   } OPTIONAL,

   /* octet 6 */
   --<noPresentBit/>
   octet6 SEQUENCE {
      eia0 BOOLEAN,
      eia1 BOOLEAN,
      eia2 BOOLEAN,
      eia3 BOOLEAN,
      eia4 BOOLEAN,
      eia5 BOOLEAN,
      eia6 BOOLEAN,
      eia7 BOOLEAN
   } OPTIONAL,

   --<noPresentBit/>
   spare OCTET STRING OPTIONAL
}

/* 9.11.3.55 - UE usage setting */
UEUsageSetting ::= SEQUENCE {
   --<is3GLength/>
   length INTEGER (0..255) DEFAULT 3, 
   spare INTEGER (0..127) DEFAULT 0, 
   usage BOOLEAN
}

/* 9.11.3.56 - UE status */
/* Defined in TS24301IEs.asn */

/* 9.11.3.57 - Uplink data status */
UplinkDataStatus ::= SEQUENCE {
   --<is3GLength/>
   length INTEGER (2..255),
   psi-7 BOOLEAN,
   psi-6 BOOLEAN,
   psi-5 BOOLEAN,
   psi-4 BOOLEAN,
   psi-3 BOOLEAN,
   psi-2 BOOLEAN,
   psi-1 BOOLEAN,
   psi-0 BOOLEAN DEFAULT FALSE,
   psi-15 BOOLEAN,
   psi-14 BOOLEAN,
   psi-13 BOOLEAN,
   psi-12 BOOLEAN,
   psi-11 BOOLEAN,
   psi-10 BOOLEAN,
   psi-9 BOOLEAN,
   psi-8 BOOLEAN,
   --<noPresentBit/>
   spare2 OCTET STRING OPTIONAL
}

/* 9.11.3.68 - UE radio capability ID */
/* Defined in TS24301IEs.asn, 9.9.3.60 */

/* 9.11.3.69 - UE radio capability ID deletion indication */
/* Defined in TS24301IEs.asn, 9.9.3.61 */

/* 9.11.3.70 - Truncated 5G-S-TMSI configuration */
TruncatedTMSIConfig ::= SEQUENCE {
   --<is3GLength/>
   length INTEGER (0..255),
   truncatedAMFId INTEGER (0..15),
   truncatedAMFPtr INTEGER (0..15)
}

/* 9.11.3.72 - N5GC indication - added in v16.6 */
N5GCIndication ::= SEQUENCE {
   spare INTEGER (0..7) DEFAULT 0,
   n5gcReg BOOLEAN
}

/* 9.11.3.73 - NB-N1 mode DRX parameters - added in v16.5 */
NBN1ModeDRXParams ::= SEQUENCE {
   --<is3GLength/>
   length INTEGER (0..255),
   spare INTEGER (0..15) DEFAULT 0,
   drxValue INTEGER (0..15)
}

/* 9.11.3.74 - Additional configuration indication - added in v16.5 */
AddlConfigIndication ::= SEQUENCE {
   spare INTEGER (0..7) DEFAULT 0,
   scmr BOOLEAN
}

/* 9.11.3.75 - Extended rejected NSSAI - added in v17.0 */
ExtRejectedNSSAIList ::= SEQUENCE {
   --<is3GLength/>
   length INTEGER (1..255),
   --<is3GVarLenList lengthElem="length"/>
   rejectedNSSAI SEQUENCE (SIZE (1..8)) OF PartialExtRejectedNSSAI
}

PartialExtRejectedNSSAI ::= SEQUENCE {  -- Added in v17.3
   spare BOOLEAN DEFAULT FALSE,
   listType PERNTypes,
   numElems INTEGER (1..15),
   --<inline/>
   backoffTimer CHOICE {
      --<selector element="listType" value="0"/>
      withoutTimer NULL,
      --<selector element="listType" value="1"/>
      timerValue GPRSTimer3 -- Type changed in v17.13
   },
   --<inline/>
   --<length expr="@numElems"/>
   rejectedSNSSAI SEQUENCE (SIZE (1..8)) OF ExtRejectedNSSAI
}

PERNTypes ::= ENUMERATED {
   pernWithoutTimer(0), pernWithTimer(1), pernTypeMAX(7)
}

ExtRejectedNSSAI ::= SEQUENCE {
   length INTEGER (1..15),
   cause  ENUMERATED { unavailInCurrPlmn(0), unavailInCurrRegisArea(1),
                       authPending(2), maxUEsReached(3), causeMAX(15) },
   sst SST,
   --<noPresentBit/>
   sd SD OPTIONAL,
   --<noPresentBit/>
   mappedSST OCTET STRING (SIZE (1)) OPTIONAL,
   --<noPresentBit/>
   mappedSD OCTET STRING (SIZE (3)) OPTIONAL
}

/* 9.11.3.76 - UE request type - added in v17.3 */
/* Defined in TS24301IEs.asn, 9.9.3.65 */

/* 9.11.3.77 - Paging restriction - added in v17.3 */
/* Defined in TS24301IEs.asn, 9.9.3.66 */

/* 9.11.3.79 - NID - added in v17.3 */
NetworkId ::= SEQUENCE {
   --<is3GLength/>
   length INTEGER (0..255),
   --<inline/>
   nid NID
}

NID ::= SEQUENCE {
   nidDigit1 INTEGER (0..15),
   assignMode INTEGER (0..15),
   nidDigit3 INTEGER (0..15),
   nidDigit2 INTEGER (0..15),
   nidDigit5 INTEGER (0..15),
   nidDigit4 INTEGER (0..15),
   nidDigit7 INTEGER (0..15),
   nidDigit6 INTEGER (0..15),
   nidDigit9 INTEGER (0..15),
   nidDigit8 INTEGER (0..15),
   spare INTEGER (0..15) DEFAULT 0,
   nidDigit10 INTEGER (0..15)
}

/* 9.11.3.80 - PEIPS assistance information - added in v17.5 */
PEIPSAssistanceInfo ::= SEQUENCE {
   --<is3GLength/>
   length INTEGER (0..255),
   --<is3GVarLenList lengthElem="length"/>
   infoTypes SEQUENCE OF PEIPSAssistInfoType
}

PEIPSAssistInfoType ::= SEQUENCE {
   type PEIPSInfoTypes,
   pagingSubgroupVal INTEGER (0..31)
}

PEIPSInfoTypes ::= ENUMERATED {
   pagingSubgroupId(0), uePagingInfo(1), peipMAX(7)
}

/* 9.11.3.81 - 5GS additional request result - added in v17.5 */
AdditionalRequestResult ::= SEQUENCE {
   --<is3GLength/>
   length INTEGER (0..255),
   spare INTEGER (0..63) DEFAULT 0,
   prd PRDTypes
}

PRDTypes ::= ENUMERATED {
   noAddlInfo(0), restrictionAccepted(1), restrictionRejected(2), prdMAX(3)
}

/* 9.11.3.82 - NSSRG information - added in v17.6 */
NSSRGInfo ::= SEQUENCE {
   --<is3GLength bitFieldSize="16"/>
   length INTEGER (1..65535),
   --<is3GVarLenList lengthElem="length"/>
   nssrgValues SEQUENCE OF NSSRGValues
}

NSSRGValues ::= SEQUENCE {
   --<is3GLength/>
   length INTEGER (0..255),
   snssai SNSSAI,
   --<noPresentBit/>
   values OCTET STRING OPTIONAL
}

/* 9.11.3.83 - List of PLMNs to be used in disaster condition - added in v17.5 */
DisasterConditionPLMNs ::= SEQUENCE {
   --<is3GLength/>
   length INTEGER (0..255),
   --<is3GVarLenList lengthElem="length"/>
   --<noPresentBit/>
   plmnIds SEQUENCE OF MCCMNCPair OPTIONAL
}

/* 9.11.3.84 - Registration wait range - added in v17.5 */
RegistrationWaitRange ::= SEQUENCE {
   --<is3GLength/>
   length INTEGER (0..255),
   minWaitTime GPRSTimer,
   maxWaitTime GPRSTimer
}

/* 9.11.3.85 - PLMN identity - added in v17.5 */
PLMNId ::= SEQUENCE {
   --<is3GLength/>
   length INTEGER (0..255),
   contents MCCMNCPair
}

/* 9.11.3.86 - Extended CAG information list - added in v17.6, modified in v18.2 */
ExtCAGInfoList ::= SEQUENCE {
   --<is3GLength bitFieldSize="16"/>
   length INTEGER (0..65535),
   --<is3GVarLenList lengthElem="length"/>
   --<noPresentBit/>
   entries SEQUENCE OF ExtCAGEntry OPTIONAL
}

ExtCAGEntry ::= SEQUENCE {
   --<is3GLength bitFieldSize="16"/>
   length INTEGER (0..65535),
   mcc-mnc MCCMNCPair,
   spare1 INTEGER (0..15) DEFAULT 0,
   caili INTEGER (0..1),
   lci BOOLEAN,
   spare2 BOOLEAN DEFAULT FALSE,
   cagOnly BOOLEAN,
   --<noPresentBit/>
   cagId OCTET STRING OPTIONAL,
   --<inline/>
   cagIdAddlInfoList CHOICE {
      --<selector element="caili" value="0"/>
      absent NULL,
      --<selector element="caili" value="1"/>
      present CAGIdAddlInfoList
   }
}

CAGIdAddlInfoList ::= SEQUENCE {
   --<is3GLength bitFieldSize="16"/>
   length INTEGER (0..65535),
   --<is3GVarLenList lengthElem="length"/>
   cagIdAddlInfo SEQUENCE OF CAGIdAddlInfo
}

CAGIdAddlInfo ::= SEQUENCE {
   --<is3GLength bitFieldSize="16"/>
   length INTEGER (0..65535),
   cagId OCTET STRING (SIZE (4)),
   spare INTEGER (0..127) DEFAULT 0,
   tvii INTEGER (0..1),
   --<inline/>
   timeValidityInfo CHOICE { -- TS 24.526, Table 5.2.1 "Time Window"
      --<selector element="tvii" value="0"/>
      absent NULL,
      --<selector element="tvii" value="1"/>
      --<inline/>
      present SEQUENCE {
         numTimePeriods INTEGER (1..255),
         --<inline/>
         --<length expr="@.numTimePeriods"/>
         timePeriodList SEQUENCE (SIZE (1..255)) OF CAGTimePeriod
      }
   }
}

CAGTimePeriod ::= SEQUENCE {
   startTime OCTET STRING (SIZE (8)),
   stopTime OCTET STRING (SIZE (8))
}

/* 9.11.3.87 - NSAG information - added in v17.7 */
NSAGInformation ::= SEQUENCE {
   --<is3GLength bitFieldSize="16"/>
   length INTEGER (5..65535),
   --<is3GVarLenList lengthElem="length"/>
   nsagEntries SEQUENCE (SIZE (1..32)) OF NSAGEntry
}

NSAGEntry ::= SEQUENCE {
   --<is3GLength/>
   length INTEGER (3..255),
   identifier INTEGER (0..255),
   snssaiList NSSAI,
   priority INTEGER (0..255),
   --<noPresentBit/>
   tai TrackingAreaIdentList OPTIONAL
}

/* 9.11.3.88 - ProSe relay transaction identity - added in v17.7 */
ProSeRelayTransactionId ::= INTEGER (0..255)

/* 9.11.3.89 - Relay key request parameters - added in v17.7 */
RelayKeyRequestParams ::= SEQUENCE {
   --<is3GLength bitFieldSize="16"/>
   length INTEGER (23..65535),
   serviceCode OCTET STRING (SIZE (3)),
   nonce OCTET STRING (SIZE (16)),
   ueIdentity RemoteUEIdentity
}

RemoteUEIdentity ::= SEQUENCE {
   spare INTEGER (0..127) DEFAULT 0,
   ruit INTEGER (0..1),
   --<inline/>
   ueid CHOICE {
      --<selector element="ruit" value="0"/>
      suci MobileIdentity-SUCI-IMSI,
      --<selector element="ruit" value="1"/>
      prukId OCTET STRING (SIZE (32))
   }
}

/* 9.11.3.90 - Relay key response parameters - added in v17.7 */
RelayKeyResponseParams ::= SEQUENCE {
   --<is3GLength bitFieldSize="16"/>
   length INTEGER (49..65535),
   key OCTET STRING (SIZE (32)),
   nonce OCTET STRING (SIZE (16)),
   cpPrukId OCTET STRING (SIZE (32)) -- Changed from CHOICE to mandatory in v17.9
}

/* 9.11.3.91 - Priority indicator - added in v17.7 */
PriorityIndicator ::= SEQUENCE {
   spare INTEGER (0..3) DEFAULT 0,
   mcsi BOOLEAN, -- Added in v18.5
   mpsi BOOLEAN
}

/* 9.11.3.92 - SNPN List - added in v18.1 */
SNPNList ::= SEQUENCE {
   --<is3GLength/>
   length INTEGER (0..255),
   --<is3GVarLenList lengthElem="length"/>
   ids SEQUENCE OF SNPNId
}

SNPNId ::= SEQUENCE {
   mccmnc MCCMNCPair,
   nid NID
}

/* 9.11.3.93 - N3IWF Address - added in v18.1 */
N3IWFAddress ::= SEQUENCE {
   --<is3GLength/>
   length INTEGER (0..255),
   type N3IWFAddressTypes,
   --<inline/>
   entry CHOICE {
      --<selector element="type" value="1"/>
      entryIpv4 OCTET STRING (SIZE (4)),
      --<selector element="type" value="2"/>
      entryIpv6 OCTET STRING (SIZE (16)),
      --<selector element="type" value="3"/>
      --<inline/>
      entryIpv4v6 SEQUENCE {
         ipv4 OCTET STRING (SIZE (4)),
         ipv6 OCTET STRING (SIZE (16))
      },
      --<selector element="type" value="4"/>
      --<inline/>
      entryFQDN SEQUENCE {
         length INTEGER (0..255),
         fqdn IA5String
      }
   }
}

N3IWFAddressTypes ::= ENUMERATED {
   ipv4(1), ipv6(2), ipv4Ipv6(3), fqdn(4), addrTypesMAX(255)
}

/* 9.11.3.94 - TNAN Information - added in v18.2 */
TNANInfo ::= SEQUENCE {
   --<is3GLength/>
   length INTEGER (0..255),
   spare INTEGER (0..63) DEFAULT 0,
   ssidInd INTEGER (0..1),
   tngfInd INTEGER (0..1),
   --<inline/>
   tngf CHOICE {
      --<selector element="tngfInd" value="0"/>
      absent NULL,
      --<selector element="tngfInd" value="1"/>
      --<inline/>
      present SEQUENCE {
         tngfIdLen INTEGER (1..255),
         --<is3GVarLenList lengthElem="tngfIdLen"/>
         tngfId OCTET STRING
      }
   },
   --<inline/>
   ss CHOICE {
      --<selector element="ssidInd" value="0"/>
      absent NULL,
      --<selector element="ssidInd" value="1"/>
      --<inline/>
      present SEQUENCE {
         ssidLen INTEGER (0..255),
         --<is3GVarLenList lengthElem="ssidLen"/>
         ssid OCTET STRING (SIZE (1..32))
      }
   }
}

/* 9.11.3.95 - RAN Timing Synchronization - added in v18.2 */
RANTimingSynch ::= SEQUENCE {
   --<is3GLength/>
   length INTEGER (0..255),
   spare INTEGER (0..127) DEFAULT 0,
   recReq BOOLEAN
}

/* 9.11.3.96 - Extended LADN Information - added in v18.2 */
ExtLADNInfo ::= SEQUENCE {
   --<is3GLength bitFieldSize="16"/>
   length INTEGER (0..65535),
   --<is3GVarLenList lengthElem="length"/>
   contents SEQUENCE OF ExtLADN
}

ExtLADN ::= SEQUENCE {
   dnn OCTET STRING,
   snssai SNSSAI,
   taiList TrackingAreaIdentList
}

/* 9.11.3.97 - Alternative NSSAI - added in v18.2 */
AlternativeNSSAI ::= SEQUENCE {
   --<is3GLength/>
   length INTEGER (0..255),
   --<is3GVarLenList lengthElem="length"/>
   entries SEQUENCE OF AltNSSAIEntry
}

AltNSSAIEntry ::= SEQUENCE {
   --<is3GLength/>
   contentsLen INTEGER (0..255),
   replacedSnssai SNSSAI,
   altSnssai SNSSAI
}

/* 9.11.3.98 - Type 6 IE Container - added in v18.2 */
Type6IEContainer ::= SEQUENCE {
   --<is3GLength bitFieldSize="16"/>
   length INTEGER (0..65535),
   --<is3GVarLenList lengthElem="length"/>
   contents SEQUENCE OF Type6IE
}

Type6IE ::= SEQUENCE {
   iei INTEGER (0..255),
   length INTEGER (0..65535),
   --<is3GVarLenList lengthElem="length"/>
   value OCTET STRING
}

/* 9.11.3.99 - Non-3GPP Access Path Switching Indication - added in v18.3 */
Non3GAccessPathSwitchInd ::= SEQUENCE {
   --<is3GLength/>
   length INTEGER (0..255),
   spare INTEGER (0..127) DEFAULT 0,
   naps BOOLEAN
}

/* 9.11.3.100 - S-NSSAI Location Validity Information - introduced in v18.4, fully defined in v18.5 */
SNSSAILocationValidityInfo ::= SEQUENCE {
   --<is3GLength bitFieldSize="16"/>
   length INTEGER (0..65535),
   --<is3GVarLenList lengthElem="length"/>
   locationInfo SEQUENCE OF LocationValidityInfo
}

LocationValidityInfo ::= SEQUENCE {
   --<is3GLength bitFieldSize="16"/>
   length INTEGER (0..65535),
   snssai SNSSAI,
   nsAoS NSAoS -- Added/defined in 18.5
   }

NSAoS ::= SEQUENCE {
   numCGIs INTEGER (0..65535),
   --<inline/>
   --<length expr="@numCGIs"/>
   cgiList SEQUENCE OF CGIList
}

/* 9.11.3.101 - S-NSSAI Time Validity Information - added in v18.4 */
SNSSAITimeValidityInfo ::= SEQUENCE {
   --<is3GLength/>
   length INTEGER (0..255),
   --<is3GVarLenList lengthElem="length"/>
   timeInfo SEQUENCE OF TimeValidityInfo
}

TimeValidityInfo ::= SEQUENCE {
   --<is3GLength/>
   length INTEGER (0..255),
   snssai SNSSAI,
   --<is3GVarLenList lengthElem="length"/>
   timeValidityInfo SEQUENCE OF PerTimeValidityInfo
}

PerTimeValidityInfo ::= SEQUENCE {
   --<is3GLength/>
   length INTEGER (0..255),
   --<is3GVarLenList lengthElem="length"/>
   timeWindows SEQUENCE OF TimeWindow
}

TimeWindow ::= SEQUENCE {
   --<is3GLength/>
   length INTEGER (0..255),
   startTime SEQUENCE {
      seconds INTEGER (0..4294967295),
      fraction INTEGER (0..4294967295)
   },
   stopTime SEQUENCE {
      seconds INTEGER (0..4294967295),
      fraction INTEGER (0..4294967295)
   },
   --<noPresentBit/>
   spare INTEGER (0..15) OPTIONAL,
   --<noPresentBit/>
   recurrencePattern INTEGER (0..15) OPTIONAL,
   --<noPresentBit/>
   recurrenceEndTime SEQUENCE {
      seconds INTEGER (0..4294967295),
      fraction INTEGER (0..4294967295)
   } OPTIONAL
}

/* 9.11.3.102 - Non-3GPP Path Switching Information - added in v18.3 */
Non3GPathSwitchingInfo ::= SEQUENCE {
   --<is3GLength/>
   length INTEGER (0..255),
   spare INTEGER (0..127) DEFAULT 0,
   nsonr BOOLEAN
}

/* 9.11.3.103 - Partial NSSAI - added in v18.4 */
PartialNSSAI ::= SEQUENCE {
   --<is3GLength bitFieldSize="16"/>
   length INTEGER (0..65535),
   --<is3GVarLenList lengthElem="length"/>
   values SEQUENCE OF PartialNSSAIInfo
}

PartialNSSAIInfo ::= SEQUENCE {
   snssai SNSSAI,
   partialTAI TrackingAreaIdentList
}

/* 9.11.3.104 - AUN3 indication - added in v18.4 */
AUN3Indication ::= SEQUENCE {
   --<is3GLength/>
   length INTEGER (0..255),
   spare INTEGER (0..127) DEFAULT 0,
   aun3reg BOOLEAN
}

/* 9.11.3.105 - Feature authorization indication - added in v18.4 */
FeatureAuthIndication ::= SEQUENCE {
   --<is3GLength/>
   length INTEGER (0..255),
   spare1 INTEGER (0..63) DEFAULT 0,
   mbsrai INTEGER (0..3),
   --<noPresentBit/>
   --<length fixed-size="0"/>
   spare2 OCTET STRING OPTIONAL
}

/* 9.11.3.106 - Payload container information */
PayloadContainerInfo ::= SEQUENCE {
   spare INTEGER (0..7) DEFAULT 0,
   pru BOOLEAN
}

/* 9.11.3.107 - AUN3 device security key - added in v18.4, renamed in v18.5 */
DeviceSecurityKey ::= SEQUENCE {
   --<is3GLength/>
   length INTEGER (0..255),
   spare INTEGER (0..63) DEFAULT 0,
   askt INTEGER (0..3),
   contentLen INTEGER (0..255),
   keyContent OCTET STRING (SIZE (64))
}

/* 9.11.3.108 - On-Demand NSSAI - added in v18.5 */
OnDemandNSSAI ::= SEQUENCE {
   --<is3GLength/>
   length INTEGER (0..255),
   --<is3GVarLenList lengthElem="length"/>
   onDemandNSSAIInfoList SEQUENCE OF OnDemandNSSAIInfo
}

OnDemandNSSAIInfo ::= SEQUENCE {
   onDemandSnssai SNSSAI,
   inactivityTimer TimeDuration
}

/* 9.11.3.109 - Extended 5GMM cause - added in v18.7 */
Ext5GCause ::= SEQUENCE {
   --<is3GLength/>
   length INTEGER (0..255),
   spare INTEGER (0..127) DEFAULT 0,
   satNR BOOLEAN
}


/* SESSION MANAGEMENT INFORMATION ELEMENTS */

/* 9.11.4.1 - SM capability */
SMCapability ::= SEQUENCE {
   --<is3GLength/>
   length INTEGER (0..255),

   /* octet 3 */
   tpmic BOOLEAN,
   atsll INTEGER (0..15),
   epts1 BOOLEAN,
   mh6Pdu BOOLEAN,
   rqos BOOLEAN,

   --<noPresentBit/>
   /* octet 4 */
   octet4 SEQUENCE { -- Added in v17.3
      spare BOOLEAN,
      mpquicudp BOOLEAN,  -- Added in v18.10
      mptcp BOOLEAN,  -- Added in v18.10
      atsssll INTEGER (0..3),  -- Added in v18.10
      spare2 BOOLEAN,
      sdnaepc BOOLEAN,  -- Added in v18.1
      apmqf BOOLEAN  -- Renamed in v18.1
   } OPTIONAL,

   --<noPresentBit/>
   spare OCTET STRING OPTIONAL
}

/* 9.11.4.2 - SM cause */
SMCause ::= INTEGER (0..255)

/* 9.11.4.3 - Always-on PDU session indication */
AlwaysOnPDUSessionInd ::= SEQUENCE {
   spare INTEGER (0..7) DEFAULT 0,
   apsi BOOLEAN
}

/* 9.11.4.4 - Always-on PDU session requested */
AlwaysOnPDUSessionReq ::= SEQUENCE {
   spare INTEGER (0..7) DEFAULT 0,
   apsr BOOLEAN
}

/* 9.11.4.5 - Allowed SSC mode */
AllowedSSCMode ::= SEQUENCE {
   spare BOOLEAN DEFAULT FALSE,
   ssc3 BOOLEAN,
   ssc2 BOOLEAN,
   ssc1 BOOLEAN
}

/* 9.11.4.7 - Integrity protection maximum data rate */
IntegrityProtMaxDataRate ::= SEQUENCE {
   maxUEDataRateUplink INTEGER (0..255),
   maxUEDataRateDownlink INTEGER (0..255)
}

/* 9.11.4.8 - Mapped EPS bearer contexts */
EPSBearerCtxts ::= SEQUENCE {
   --<is3GLength bitFieldSize="16"/>
   length INTEGER (7..65535),
   --<is3GVarLenList lengthElem="length"/>
   epsBearerCtxts SEQUENCE OF EPSBearerCtxt
}

EPSBearerCtxt ::= SEQUENCE {
   bearerId INTEGER (0..255),
   bearerCtxtLen INTEGER (0..65535),
   opCode INTEGER (0..3),
   spare BOOLEAN DEFAULT FALSE,
   eBit BOOLEAN,
   numParams INTEGER (0..15),
   --<inline/>
   --<length expr="@numParams"/>
   --<noPresentBit/>
   paramsList SEQUENCE (SIZE (0..15)) OF EPSParam OPTIONAL
}

EPSParam ::= SEQUENCE {
   id EPSParamId,
   --<inline/>
   content CHOICE {
      --<selector element="id" value="1"/>
      epsQoS EPSQualityOfService,
      --<selector element="id" value="2"/>
      extEpsQos ExtQualityOfService,
      --<selector element="id" value="3"/>
      tft TFT,
      --<selector element="id" value="4"/>
      apnAmbr APNAggMaxBitRate,
      --<selector element="id" value="5"/>
      extApnAmbr ExtAPNAggMaxBitRate
   }
}

EPSParamId ::= ENUMERATED {
   epsQoS(1), extEpsQoS(2), tft(3),
   apnAmbr(4), extApnAmbr(5), epsParamMax(255), ...
}

/* 9.11.4.9 - Maximum number of supported packet filters */
MaxSupportedPacketFilters ::= SEQUENCE {
   maxFilters INTEGER (1..2047),
   spare INTEGER (0..31) DEFAULT 0
}

/* 9.11.4.10 - PDU address */
PDUAddress ::= SEQUENCE {
   --<is3GLength/>
   length INTEGER (1..255),
   spare INTEGER (0..15) DEFAULT 0,
   s16LLA INTEGER (0..1),  -- Added in v16.6
   sessionType PDUAddressValues,
   --<inline/>
   addressInfo CHOICE {
      --<selector element="sessionType" value="1"/>
      addressInfoIpv4 OCTET STRING (SIZE (4)),
      --<selector element="sessionType" value="2"/>
      addressInfoIpv6 OCTET STRING (SIZE (8)),
      --<selector element="sessionType" value="3"/>
      --<inline/>
      addressInfoIpv4v6 SEQUENCE {
         ipv6 OCTET STRING (SIZE (8)),
         ipv4 OCTET STRING (SIZE (4))
      }
   },
   --<inline/>
   smfIp6Addr CHOICE {  -- Added in v16.6
      --<selector element="s16LLA" value="0"/>
      absent NULL,
      --<selector element="s16LLA" value="1"/>
      present OCTET STRING (SIZE (16))
   }
}

PDUAddressValues ::= ENUMERATED {
   ipv4(1), ipv6(2), ipv4v6(3), pduAddrValMAX(7)
}

/* 9.11.4.11 - PDU session type */
PDUSessionType ::= SEQUENCE {
   spare BOOLEAN DEFAULT FALSE,
   sessionType SessionType
}

SessionType ::= ENUMERATED {
   st-ipv4(1), st-ipv6(2), st-ipv4v6(3), st-unstructured(4), st-eth(5),
   st-MAX(7)
}

/* 9.11.4.12 - QoS flow descriptions */
QOSFlowDescriptions ::= SEQUENCE {
   --<is3GLength bitFieldSize="16"/>
   length INTEGER (3..65535),
   --<is3GVarLenList lengthElem="length"/>
   qosFlowDesr SEQUENCE OF QOSFlowDescription
}

QOSFlowDescription ::= SEQUENCE {
   spare INTEGER (0..3) DEFAULT 0,
   qfi INTEGER (0..63),
   opCode FlowOpCodes,
   spare2 INTEGER (0..31) DEFAULT 0,
   spare3 BOOLEAN DEFAULT FALSE,
   eBit BOOLEAN,
   numParams INTEGER (0..63),
   --<inline/>
   --<length expr="@numParams"/>
   --<noPresentBit/>
   paramsList SEQUENCE (SIZE (0..63)) OF Parameter OPTIONAL
}

FlowOpCodes ::= ENUMERATED {
   flowCreate(1), flowDelete(2), flowModify(3), ruleOpMax(7)
}

Parameter ::= SEQUENCE {
   id ParameterId,
   --<is3GLength/>
   length INTEGER(0..255),
   --<inline/>
   content CHOICE {
      --<selector element="id" value="1"/>
      fiveQI INTEGER(0..255),
      --<selector element="id" value="2"/>
      gfbrUL SEQUENCE {
         unit FlowRateUnit,
         guarFlow INTEGER(0..65535)
      },
      --<selector element="id" value="3"/>
      gfbrDL SEQUENCE {
         unit FlowRateUnit,
         guarFlow INTEGER(0..65535)
      },
      --<selector element="id" value="4"/>
      mfbrUL  SEQUENCE {
         unit FlowRateUnit,
         guarFlow INTEGER(0..65535)
      },
      --<selector element="id" value="5"/>
      mfbrDL  SEQUENCE {
         unit FlowRateUnit,
         guarFlow INTEGER(0..65535)
      },
      --<selector element="id" value="6"/>
      avgWindow INTEGER(0..65535),
      --<selector element="id" value="7"/>
      epsBearerIdent SEQUENCE {
         value INTEGER(0..15),
         spare INTEGER(0..15) DEFAULT 0
      },
      --<length fixed-size="0"/>
      unknown OCTET STRING
   }
}

ParameterId ::= ENUMERATED {
   fiveQI(1), gfbrUL(2), gfbrDL(3), mfbrUL(4), mfbrDL(5),
   avgWindow(6), epsBearerIdent(7), paramIdMax(255), ...
}

FlowRateUnit ::= INTEGER {
   notUsed(0), kbps-1(1), kbps-4(2), kbps-16(3), kbps-64(4),
   kbps-256(5), mbps-1(6), mbps-4(7), mbps-16(8), mbps-64(9),
   mbps-256(10), gbps-1(11), gbps-4(12), gbps-16(13), gbps-64(14),
   gbps-256(15), tbps-1(16), tbps-4(17), tbps-16(18), tbps-64(19),
   tbps-256(20), pbps-1(21), pbps-4(22), pbps-16(23), pbps-64(24),
   pbps-256(25) } (0..255)

/* 9.11.4.13 - QoS rules */
QoSRules ::= SEQUENCE {
   --<is3GLength bitFieldSize="16"/>
   length INTEGER (0..65535),
   --<is3GVarLenList lengthElem="length"/>
   rules SEQUENCE OF QoSRule
}

QoSRule ::= SEQUENCE {
   ruleId INTEGER (0..255),
   --<is3GLength bitFieldSize="16"/>
   ruleLen INTEGER (0..65535),
   ruleOpCode RuleOpCodes,
   dqr BOOLEAN,
   numPacketFilters INTEGER (0..15),
   --<inline/>
   packetFilterList CHOICE {
      --<selector element="ruleOpCode" value="1"/>
      --<length expr="@numPacketFilters"/>
      createNew SEQUENCE (SIZE (0..15)) OF PFCreateNew,
      --<selector element="ruleOpCode" value="2"/>
      delete NULL,
      --<selector element="ruleOpCode" value="3"/>
      --<length expr="@numPacketFilters"/>
      modifyAndAdd SEQUENCE (SIZE (1..15)) OF PFCreateNew,
      --<selector element="ruleOpCode" value="4"/>
      --<length expr="@numPacketFilters"/>
      modifyAndReplace SEQUENCE (SIZE (0..15)) OF PFCreateNew,
      --<selector element="ruleOpCode" value="5"/>
      --<length expr="@numPacketFilters"/>
      modifyAndDelete SEQUENCE (SIZE (1..15)) OF PFModifyAndDelete,
      --<selector element="ruleOpCode" value="6"/>
      modifyNoModify NULL
   },
   --<noPresentBit/>
   precedence INTEGER (0..255) OPTIONAL, -- Made optional in v17.10
   --<noPresentBit/>
   octet SEQUENCE { -- Made optional in v17.10
      spare BOOLEAN DEFAULT FALSE,
      segregation BOOLEAN,
      flowId INTEGER (0..63)
   } OPTIONAL
}

RuleOpCodes ::= ENUMERATED {
   createNew(1), delete(2), modifyAndAdd(3), modifyAndReplace(4), 
   modifyAndDelete(5), modifyNoModify(6), ruleOpMax(7)
}

PFModifyAndDelete ::= SEQUENCE {
   spare INTEGER (0..15) DEFAULT 0,
   filterId INTEGER (0..15)
}

PFCreateNew ::= SEQUENCE {
   spare INTEGER (0..3) DEFAULT 0,
   filterDirection INTEGER (0..3),
   filterId INTEGER (0..15),
   --<is3GLength/>
   filterContentLen INTEGER (0..255),
   --<is3GVarLenList lengthElem="filterContentLen"/>
   filterContent SEQUENCE OF PFComponent
}

PFComponent ::= SEQUENCE {
   typeId PacketFilterTypeId,
   --<inline/>
   value CHOICE {
      --<selector element="typeId" value="1"/>
      matchAll NULL,
      --<selector element="typeId" value="16"/>
      ipv4Remote OCTET STRING (SIZE (8)),
      --<selector element="typeId" value="17"/>
      ipv4Local OCTET STRING (SIZE (8)),
      --<selector element="typeId" value="33"/>
      ipv6Remote OCTET STRING (SIZE (17)),
      --<selector element="typeId" value="35"/>
      ipv6Local OCTET STRING (SIZE (17)),
      --<selector element="typeId" value="48"/>
      protId OCTET STRING (SIZE (1)),
      --<selector element="typeId" value="64"/>
      singleLocalPort OCTET STRING (SIZE (2)),
      --<selector element="typeId" value="65"/>
      localPortRange OCTET STRING (SIZE (4)),
      --<selector element="typeId" value="80"/>
      singleRemPort OCTET STRING (SIZE (2)),
      --<selector element="typeId" value="81"/>
      remPortRange OCTET STRING (SIZE (4)),
      --<selector element="typeId" value="96"/>
      secParam OCTET STRING (SIZE (4)),
      --<selector element="typeId" value="112"/>
      typeOfSvc OCTET STRING (SIZE (2)),
      --<selector element="typeId" value="128"/>
      flowLabel OCTET STRING (SIZE (3)),
      --<selector element="typeId" value="129"/>
      destMacAddr OCTET STRING (SIZE (6)),
      --<selector element="typeId" value="130"/>
      srcMacAddr OCTET STRING (SIZE (6)),
      --<selector element="typeId" value="131"/>
      ctagVid OCTET STRING (SIZE (2)),
      --<selector element="typeId" value="132"/>
      stagVid OCTET STRING (SIZE (2)),
      --<selector element="typeId" value="133"/>
      ctagPcp OCTET STRING (SIZE (1)),
      --<selector element="typeId" value="134"/>
      stagPcp OCTET STRING (SIZE (1)),
      --<selector element="typeId" value="135"/>
      ethernet OCTET STRING (SIZE (2)),
      --<selector element="typeId" value="136"/>
      destMacAddrRange OCTET STRING (SIZE (12)), -- added in 17.4
      --<selector element="typeId" value="137"/>
      srcMacAddrRange OCTET STRING (SIZE (12)) -- added in 17.4
   }
}

PacketFilterTypeId ::= ENUMERATED {
   matchAll(1), ipv4Remote(16), ipv4Local(17), ipv6Remote(33), ipv6Local(35),
   protId(48), singleLocalPort(64), localPortRange(65), singleRemPort(80),
   remPortRange(81), secParam(96), typeOfSvc(112), flowLabel(128),
   destMacAddr(129), srcMacAddr(130), ctagVid(131), stagVid(132),
   ctagPcp(133), stagPcp(134), ethernet(135),
   destMacAddrRange(136), srcMacAddrRange(137), typeIdMax(255)
}

/* 9.11.4.14 - Session AMBR */
SessionAMBR ::= SEQUENCE {
   --<is3GLength/>
   length INTEGER (0..255) DEFAULT 8,
   unitAmbrDL INTEGER (0..255),
   sessionAmbrDL INTEGER (0..65535),
   unitAmbrUL INTEGER (0..255),
   sessionAmbrUL INTEGER (0..65535)
}

/* 9.11.4.15 - SM PDU DN request container */
SmPduDnReqContainer ::= SEQUENCE {
   --<is3GLength/>
   length INTEGER (3..255),
   --<is3GVarLenList lengthElem="length"/>
   --<noPresentBit/>
   dnSpecificId OCTET STRING OPTIONAL
}

/* 9.11.4.16 - SSC mode */
SSCMode ::= SEQUENCE {
   spare BOOLEAN DEFAULT FALSE,
   sscMode SSCModeValue
}

SSCModeValue ::= ENUMERATED {
   ssc-mode1(1), ssc-mode2(2), ssc-mode3(3), ssc-MAX(7)
}

/* 9.11.4.17 - Re-attempt indicator */
ReattemptIndicator ::= SEQUENCE {
   --<is3GLength/>
   length INTEGER (1),
   spare INTEGER (0..63) DEFAULT 0,
   eplmnc BOOLEAN,
   ratc BOOLEAN
}

/* 9.11.4.18 - 5GSM network feature support */
SMNetworkFeatureSupport ::= SEQUENCE {
   --<is3GLength/>
   length INTEGER (1..255), 
   spare INTEGER (0..63) DEFAULT 0, 
   naps BOOLEAN, -- added in v18.3
   eptS1 BOOLEAN,
   --<noPresentBit/>
   --<length fixed-size="0"/>
   spare2 OCTET STRING OPTIONAL
}

/* 9.11.4.21 - 5GSM congestion re-attempt indicator */
CongestionReattemptIndicator ::= SEQUENCE {
   --<is3GLength/>
   length INTEGER (1..255),
   spare INTEGER (0..63) DEFAULT 0,
   catbo BOOLEAN,
   abo BOOLEAN
}

/* 9.11.4.22 - ATSSS container - see TS 24.193, Section 6.1.2 */
ATSSSContainer ::= SEQUENCE {
   --<is3GLength bitFieldSize="16"/>
   length INTEGER (3..65535),
   --<is3GVarLenList lengthElem="length"/>
   --<noPresentBit/>
   contents SEQUENCE OF ATSSSParamList OPTIONAL -- ATSSS container contents, Fig 6.1.2-1
}

ATSSSParamList ::= SEQUENCE { -- ATSSS parameter, Fig 6.1.2-2
   paramId INTEGER (1..255),
   --<is3GLength bitFieldSize="16"/>
   length INTEGER (3..65535),
   --<inline/>
   contents CHOICE {
      --<selector element="paramId" value="1"/>
      --<length fixed-size="0"/>
      rules SEQUENCE OF ATSSSRules,
      --<selector element="paramId" value="2"/>
      mptcpSteering NetworkSteeringInfo,
      --<selector element="paramId" value="3"/>
      measAssistance MeasurementAssistance,
      --<selector element="paramId" value="4"/>
      mpquicSteering NetworkSteeringInfo
   }
}

ATSSSRules ::= SEQUENCE {
   --<is3GLength bitFieldSize="16"/>
   length INTEGER (0..65535),
   id INTEGER (1..255),
   operation INTEGER (1..255),
   precedence INTEGER (1..255),
   trafficDesc SEQUENCE {
      --<is3GLength bitFieldSize="16"/>
      numElements INTEGER (1..65535),
      --<is3GVarLenList lengthElem="length"/>
      elements SEQUENCE OF TrafficDescriptor -- Changed in v18.5
   },
   selectionDesc AccessSelectionDescriptor
}

TrafficDescriptor ::= SEQUENCE { -- Added in v18.5
   type INTEGER (1..255),
   --<inline/>
   value CHOICE {
      --<selector element="type" value="1"/>
      matchAll NULL,
      --<selector element="type" value="8"/>
      osIds SEQUENCE {
         osId OCTET STRING (SIZE (16)),
         osAppId LenWithOctStrVal
      },
      --<selector element="type" value="16"/>
      ipv4RemoteAddr SEQUENCE {
         ipv4Addr OCTET STRING (SIZE (4)),
         ipv4Mask OCTET STRING (SIZE (4))
      },
      --<selector element="type" value="33"/>
      ipv6RemoteAddr SEQUENCE {
         ipv6Addr OCTET STRING (SIZE (16)),
         ipv6Len INTEGER (0..255)
      },
      --<selector element="type" value="48"/>
      protocolId INTEGER (0..255),
      --<selector element="type" value="80"/>
      remotePort INTEGER (0..65535),
      --<selector element="type" value="81"/>
      remotePortRange SEQUENCE {
         lowLimit INTEGER (0..65535),
         highLimit INTEGER (0..65535)
      },
      --<selector element="type" value="82"/>
      ip3Tuple IP3Tuple,
      --<selector element="type" value="96"/>
      paramIndex OCTET STRING (SIZE (4)),
      --<selector element="type" value="112"/>
      serviceType SEQUENCE {
         class INTEGER (0..255),
         mask INTEGER (0..255)
      },
      --<selector element="type" value="128"/>
      flowLabel OCTET STRING (SIZE (3)),
      --<selector element="type" value="129"/>
      macAddr OCTET STRING (SIZE (6)),
      --<selector element="type" value="131"/>
      ctagVid INTEGER (0..65535),
      --<selector element="type" value="132"/>
      stagVid INTEGER (0..65535),
      --<selector element="type" value="133"/>
      ctagPcp INTEGER (0..255),
      --<selector element="type" value="134"/>
      stagPcp INTEGER (0..255),
      --<selector element="type" value="135"/>
      etherType INTEGER (0..65535),
      --<selector element="type" value="136"/>
      dnn DNNList,
      --<selector element="type" value="144"/>
      connCapabilities NumWithOctStrVal,
      --<selector element="type" value="145"/>
      fqdn SEQUENCE {
         length INTEGER (0..255),
         value PrintableString
      },
      --<selector element="type" value="146"/>
      regularExpr LenWithOctStrVal,
      --<selector element="type" value="160"/>
      osAppId LenWithOctStrVal,
      --<selector element="type" value="161"/>
      macAddrRange SEQUENCE {
         lowLimit OCTET STRING (SIZE (6)),
         highLimit OCTET STRING (SIZE (6))
      },
      --<selector element="type" value="162"/>
      pinId LenWithOctStrVal,
      --<selector element="type" value="163"/>
      groupId LenWithOctStrVal
   }
}

IP3Tuple ::= SEQUENCE {
   spare INTEGER (0..7) DEFAULT 0,
   ipv4AddrPresent INTEGER (0..1),
   ipv6AddrPresent INTEGER (0..1),
   protIdPresent INTEGER (0..1),
   portPresent INTEGER (0..1),
   portRangePresent INTEGER (0..1),
   --<inline/>
   ipv4Addr CHOICE {
      --<selector element="ipv4AddrPresent" value="0"/>
      absent NULL,
      --<selector element="ipv4AddrPresent" value="1"/>
      present SEQUENCE {
         address OCTET STRING (SIZE (4)),
         mask OCTET STRING (SIZE (4))
      }
   },
   --<inline/>
   ipv6Addr CHOICE {
      --<selector element="ipv6AddrPresent" value="0"/>
      absent NULL,
      --<selector element="ipv6AddrPresent" value="1"/>
      present SEQUENCE {
         address OCTET STRING (SIZE (16)),
         prefixLen INTEGER (0..255)
      }
   },
   --<inline/>
   protocolId CHOICE {
      --<selector element="protIdPresent" value="0"/>
      absent NULL,
      --<selector element="protIdPresent" value="1"/>
      present INTEGER (0..255)
   },
   --<inline/>
   port CHOICE {
      --<selector element="portPresent" value="0"/>
      absent NULL,
      --<selector element="portPresent" value="1"/>
      present INTEGER (0..65535)
   },
   --<inline/>
   portRange CHOICE {
      --<selector element="portRangePresent" value="0"/>
      absent NULL,
      --<selector element="portRangePresent" value="1"/>
      present SEQUENCE {
         lowLimit OCTET STRING (SIZE (2)),
         highLimit OCTET STRING (SIZE (2))
      }
   }
}

LenWithOctStrVal ::= SEQUENCE {
   --<is3GLength/>
   length INTEGER (0..255),
   --<is3GVarLenList lengthElem="length"/>
   value SEQUENCE OF OCTET STRING
}

NumWithOctStrVal ::= SEQUENCE {
   numVals INTEGER (0..255),
   --<inline/>
   --<length expr="@numVals"/>
   values SEQUENCE OF OCTET STRING
}

AccessSelectionDescriptor ::= SEQUENCE {
   --<is3GLength/>
   length INTEGER (1..255),
   functionality INTEGER (1..255),
   mode INTEGER (1..255),
   --<noPresentBit/>
   modeInfo INTEGER (1..255) OPTIONAL,
   --<noPresentBit/>
   addlIndicator SEQUENCE {
      spare INTEGER (0..63) DEFAULT 0,
      lbpao INTEGER (0..3)
   } OPTIONAL,
   --<noPresentBit/>
   thresholdValue SEQUENCE {
      --<is3GLength/>
      length INTEGER (1..255),
      maxRTTValue INTEGER (1..65535),
      maxPktLossRate INTEGER (1..255)
   } OPTIONAL,
   --<noPresentBit/>
   transportMode INTEGER (1..255) OPTIONAL
}

NetworkSteeringInfo ::= SEQUENCE {
   client3GAddrType INTEGER (1..255),
   --<inline/>
   client3GAddr CHOICE {
      --<selector element="client3GAddrType" value="1"/>
      ipv4 OCTET STRING (SIZE (4)),
      --<selector element="client3GAddrType" value="2"/>
      ipv6 OCTET STRING (SIZE (16)),
      --<selector element="client3GAddrType" value="3"/>
      ipv4v6 OCTET STRING (SIZE (20))
   },
   clientNon3GAddrType INTEGER (1..255),
   --<inline/>
   clientNon3GAddr CHOICE {
      --<selector element="clientNon3GAddrType" value="1"/>
      ipv4 OCTET STRING (SIZE (4)),
      --<selector element="clientNon3GAddrType" value="2"/>
      ipv6 OCTET STRING (SIZE (16)),
      --<selector element="clientNon3GAddrType" value="3"/>
      ipv4v6 OCTET STRING (SIZE (20))
   },
   --<is3GLength/>
   proxyLen INTEGER (1..255),
   --<is3GVarLenList lengthElem="proxyLen"/>
   proxyValues SEQUENCE OF ProxyInfo
}

ProxyInfo ::= SEQUENCE {
   addrType INTEGER (1..255),
   --<inline/>
   address CHOICE {
      --<selector element="addrType" value="1"/>
      ipv4 OCTET STRING (SIZE (4)),
      --<selector element="addrType" value="2"/>
      ipv6 OCTET STRING (SIZE (16)),
      --<selector element="addrType" value="3"/>
      ipv4v6 OCTET STRING (SIZE (20))
   },
   port INTEGER (1..65535),
   proxyType INTEGER (1..255)
}

MeasurementAssistance ::= SEQUENCE {
   addrType INTEGER (1..255),
   --<inline/>
   address CHOICE {
      --<selector element="addrType" value="1"/>
      ipv4 OCTET STRING (SIZE (4)),
      --<selector element="addrType" value="2"/>
      ipv6 OCTET STRING (SIZE (16)),
      --<selector element="addrType" value="3"/>
      ipv4v6 OCTET STRING (SIZE (20))
   },
   port3G INTEGER (1..65535),
   portNon3G INTEGER (1..65535),
   spare INTEGER (0..63) DEFAULT 0,
   apmqf BOOLEAN,
   aari BOOLEAN,
   --<is3GLength/>
   flowLen INTEGER (1..255),
   --<is3GVarLenList lengthElem="flowLen"/>
   flows SEQUENCE OF QoSFlow
}

QoSFlow ::= SEQUENCE {
   spare INTEGER (0..3) DEFAULT 0,
   qfi INTEGER (0..63),
   macAddr3G OCTET STRING (SIZE(2|6)), -- or port
   macAddrNon3G OCTET STRING (SIZE(2|6)) -- or port
}

/* 9.11.4.23 - Control plane only indication */
ControlPlaneIndication ::= SEQUENCE {
   spare INTEGER (0..7) DEFAULT 0,
   cpoi BOOLEAN
}

/* 9.11.4.24 - Header compression configuration */
/* Defined in TS24301IEs.asn, 9.9.4.22 */

/* 9.11.4.25 - DS-TT Ethernet port MAC address */
DSTTEthMACAddr ::= SEQUENCE {
   --<is3GLength/>
   length INTEGER (1..255),
   contents OCTET STRING (SIZE(6))
}

/* 9.11.4.26 - DS-TT residence time */
DSTTResidenceTime ::= SEQUENCE {
   --<is3GLength/>
   length INTEGER (1..255),
   contents OCTET STRING (SIZE(8))
}

/* 9.11.4.27 - Port management information container */
PortMgmtInfoContainer ::= SEQUENCE {
   --<is3GLength bitFieldSize="16"/>
   length INTEGER (0..65535),
   --<is3GVarLenList lengthElem="length"/>
   container OCTET STRING (SIZE (1..65535))
}

/* 9.11.4.28 - Ethernet header compression configuration - added in v16.5 */
EthHdrCompressConfig ::= SEQUENCE {
   --<is3GLength/>
   length INTEGER (1..255),
   spare INTEGER (0..63) DEFAULT 0,
   cidLength INTEGER (0..3)
}

/* 9.11.4.29 - Remote UE context list - added in v17.4 */
/* This is not quite the same as the 24.301 version of this IE; thus,
   this 24.501 version needs to be defined... */
RemoteUEContextList ::= SEQUENCE {
   --<is3GLength bitFieldSize="16"/>
   length INTEGER (0..65535),
   numUECtxts INTEGER (1..255), 
   --<inline/>
   --<length expr="@numUECtxts"/>
   contexts SEQUENCE OF RemoteUEContext
}

RemoteUEContext ::= SEQUENCE { -- Layout updated in v17.8
   --<is3GLength/>
   contextLength INTEGER (0..255),
   spare1 INTEGER (0..15) DEFAULT 0,
   ueidFormat BOOLEAN,
   ueidType UEIDTypes,
   ueidLength INTEGER (0..255),
   --<inline/>
   --<length expr="@ueidLength"/>
   ueid OCTET STRING (SIZE (8..254)),
   --<noPresentBit/>
   spare2 INTEGER (0..7) OPTIONAL,
   --<noPresentBit/>
   upri4i BOOLEAN OPTIONAL,
   --<noPresentBit/>
   tpri4i BOOLEAN OPTIONAL,
   --<noPresentBit/>
   protocol RemoteUEProtocols OPTIONAL,
   --<inline/>
   addrInfo CHOICE {
      --<selector element="protocol" value="0"/>
      noIp NULL,
      --<selector element="protocol" value="1"/>
      ipv4 OCTET STRING (SIZE (4..12)),
      --<selector element="protocol" value="2"/>
      ipv6 OCTET STRING (SIZE (8)),
      --<selector element="protocol" value="4"/>
      unstructured NULL,
      --<selector element="protocol" value="5"/>
      ethernet OCTET STRING (SIZE (6))
   },
   --<inline/>
   hplmnId CHOICE {
      --<selector element="ueidType" value="1"/>
      plmnId PLMNId,
      --<selector element="ueidType" value="2"/>
      absent NULL
   }
}

UEIDTypes ::= ENUMERATED {
   upPrukId(1), cpPrukId(2), imei(3), imeisv(4), ueidTypeMAX(7)
}

RemoteUEProtocols ::= ENUMERATED {
   noIp(0), ipv4(1), ipv6(2), unstructured(4), ethernet(5), protMAX(7)
}

/* 9.11.4.30 - Requested MBS container - added in v17.4 */
RequestedMBSContainer ::= SEQUENCE {
   --<is3GLength bitFieldSize="16"/>
   length INTEGER (0..65535), -- Changed to 2 octets in v17.7
   --<is3GVarLenList lengthElem="length"/>
   --<storage>array</storage>
   sessionInfo SEQUENCE (SIZE (1..256)) OF MBSSessionInfo
}

MBSSessionInfo ::= SEQUENCE {
   spare INTEGER (0..15) DEFAULT 0,
   operation MBSOperations,
   type MBSSessionIdTypes,
   --<inline/>
   id CHOICE {
      --<selector element="type" value="1"/>
      tmgi TMGI,
      --<selector element="type" value="2"/>
      ipv4 SEQUENCE {
         srcAddrInfo OCTET STRING (SIZE (4)),
         destAddrInfo OCTET STRING (SIZE (4))
      },
      --<selector element="type" value="3"/>
      ipv6 SEQUENCE {
         srcAddrInfo OCTET STRING (SIZE (16)),
         destAddrInfo OCTET STRING (SIZE (16))
      }
   }
}

MBSOperations ::= ENUMERATED {
   join(1), leave(2), mbsopsMAX(3)
}

MBSSessionIdTypes ::= ENUMERATED {
   tmgi(1), ipv4(2), ipv6(3)
}

/* 9.11.4.31 - Received MBS container - added in v17.4 */
ReceivedMBSContainer ::= SEQUENCE {
   --<is3GLength bitFieldSize="16"/>
   length INTEGER (0..65535),
   --<is3GVarLenList lengthElem="length"/>
   receivedInfo SEQUENCE OF ReceivedMBSInfo
}

ReceivedMBSInfo ::= SEQUENCE {
   rejectionCause INTEGER (0..7),
   msai MSAITypes,
   md INTEGER (0..7),
   spare INTEGER (0..7) DEFAULT 0,
   ipat BOOLEAN,  -- Added in v17.9
   msci INTEGER (0..1),
   mti MTITypes,
   ipae INTEGER (0..1),
   tmgi TMGI,
   --<inline/>
   ipAddrInfo CHOICE {
      --<selector element="ipae" value="0"/>
      notIncluded NULL,
      --<selector element="ipae" value="1"/>
      included SEQUENCE {
         srcAddrInfo OCTET STRING (SIZE (4..16)),
         destAddrInfo OCTET STRING (SIZE (4..16))
      }
   },
   --<inline/>
   serviceArea CHOICE {
      --<selector element="msai" value="0"/>
      notIncluded NULL,
      --<selector element="msai" value="1"/>
      tai TrackingAreaIdentList,
      --<selector element="msai" value="2"/>
      --<length fixed-size="0"/>
      cgi SEQUENCE OF CGIList,
      --<selector element="msai" value="3"/>
      taiAndCgi SEQUENCE {
         tai TrackingAreaIdentList,
         --<length fixed-size="0"/>
         cgi SEQUENCE OF CGIList
      }
   },
   --<inline/>
   timer CHOICE {
      --<selector element="mti" value="0"/>
      notIncluded NULL,
      --<selector element="mti" value="1"/>
      startTime TimeZoneAndTime,
      --<selector element="mti" value="2"/>
      backoffTimer GPRSTimer
   },
   --<inline/>
   securityContainer CHOICE { -- Layout updated in v17.8
      --<selector element="msci" value="0"/>
      notIncluded NULL,
      --<selector element="msci" value="1"/>
      included SEQUENCE {
         numKeySets INTEGER (1..255),
         --<inline/>
         --<length expr="@.numKeySets"/>
         keySetList SEQUENCE (SIZE (1..255)) OF MBSSecurityKeySet
      }
   }
}

MSAITypes ::= ENUMERATED {
   notIncluded(0), inclTAI(1), inclCGI(2), inclTAICGI(3)
}

MTITypes ::= ENUMERATED {
   noTimers(0), startTime(1), backoffTimer(2), mtiMAX(3)
}

CGIList ::= SEQUENCE {
   nrCellId OCTET STRING (SIZE (5)),
   pair MCCMNCPair
}

MBSSecurityKeySet ::= SEQUENCE {
   spare INTEGER (0..127) DEFAULT 0,
   mtki INTEGER (0..1),
   keyDomainId MCCMNCPair,
   mskId OCTET STRING (SIZE (4)),
   msk OCTET STRING (SIZE (16)),
   --<inline/>
   mtkInfo CHOICE {
      --<selector element="mtki" value="0"/>
      notIncluded NULL,
      --<selector element="mtki" value="1"/>
      included SEQUENCE {
         mtkId OCTET STRING (SIZE (2)),
         mtk OCTET STRING (SIZE (16))
      }
   }
}

/* 9.11.4.32 - PDU session pair ID - added in v17.5 */
PDUSessionPairId ::= SEQUENCE {
   --<is3GLength/>
   length INTEGER (1..255),
   id PDUPairIds
}

PDUPairIds ::= ENUMERATED {
   pairId0(0), pairId1(1), pairId2(2), pairId3(3), pairId4(4),
   pairId5(5), pairId6(6), ppiMAX(255)
}

/* 9.11.4.33 - RSN - added in v17.5 */
RSN ::= SEQUENCE {
   --<is3GLength/>
   length INTEGER (1..255),
   rsn INTEGER (0..255)
}

/* 9.11.4.34 - ECS address - added in v17.6 but not included in any messages as of v18.10 */
ECSAddress ::= SEQUENCE {
   --<is3GLength bitFieldSize="16"/>
   length INTEGER (0..65535),
   addressType ECSAddrTypes,
   spatialValidityType SpatialValidityTypes,
   --<inline/>
   address CHOICE {
      --<selector element="addressType" value="0"/>
      ipv4 OCTET STRING (SIZE (4)),
      --<selector element="addressType" value="1"/>
      ipv6 OCTET STRING (SIZE (16)),
      --<selector element="addressType" value="2"/>
      fqdn SEQUENCE {
         fqdnLen INTEGER (1..255),
         fqdnValue PrintableString
      },
      --<selector element="addressType" value="15"/>
      notIncluded NULL
   },
   --<noPresentBit/>
   contentsLen INTEGER (0..65535) OPTIONAL,
   --<noPresentBit/>
   --<inline/>
   contentsInfo CHOICE {
      --<selector element="spatialValidityType" value="0"/>
      none NULL,
      --<selector element="spatialValidityType" value="1"/>
      geoArea SEQUENCE {
         shapeType INTEGER (0..15),
         numPointsOrSpare INTEGER (0..15),
         description OCTET STRING (SIZE (6..90))
      },
      --<selector element="spatialValidityType" value="2"/>
      trackArea TrackingAreaIdent,
      --<selector element="spatialValidityType" value="3"/>
      country MCCMNCPair
   } OPTIONAL,
   --<noPresentBit/>
   spare INTEGER (0..63) OPTIONAL, -- Added in v18.7
   --<noPresentBit/>
   espili INTEGER (0..1) OPTIONAL, -- Added in v18.8
   --<noPresentBit/>
   eami INTEGER (0..1) OPTIONAL, -- Added in v18.7
   --<noPresentBit/>
   --<inline/>
   ecsAuthMethods CHOICE { -- Added in v18.7
      --<selector element="eami" value="0"/>
      absent NULL,
      --<selector element="eami" value="1"/>
      present SEQUENCE {
         spare INTEGER (0..31) DEFAULT 0,
         tlsgi BOOLEAN,
         tlsai BOOLEAN,
         tlscsci BOOLEAN
      }
   },
   --<noPresentBit/>
   --<inline/>
   ecsSupportedInfoList CHOICE { -- Added in v18.8
      --<selector element="espili" value="0"/>
      absent NULL,
      --<selector element="espili" value="1"/>
      present ECSSupportedInfoList
   }
}

ECSAddrTypes ::= ENUMERATED {
   eatIpv4(0), eatIpv6(1), eatFqdn(2), eatUnspecified(15)
}

SpatialValidityTypes ::= ENUMERATED {
   svtNone(0), svtGeographicalArea(1), svtTrackingArea(2), svtCountryWide(3),
   svtMAX(15)
}

ECSSupportedInfoList ::= SEQUENCE {
   --<is3GLength bitFieldSize="16"/>
   length INTEGER (0..65535),
   --<is3GVarLenList lengthElem="length"/>
   supportedInfo SEQUENCE OF SupportedPLMNInfo
}

SupportedPLMNInfo ::= SEQUENCE {
   --<is3GLength bitFieldSize="16"/>
   length INTEGER (0..65535),
   plmnId MCCMNCPair,
   --<is3GVarLenList lengthElem="length"/>
   ecspInfo SEQUENCE OF ECSPInfo
}

ECSPInfo ::= SEQUENCE {
   length INTEGER (0..65535),
   --<length fixed-size="0"/>
   ecspId IA5String
}

/* 9.11.4.36 - N3QAI - added in v18.3 */
N3QAI ::= SEQUENCE {
   --<is3GLength bitFieldSize="16"/>
   length INTEGER (0..65535),
   --<is3GVarLenList lengthElem="length"/>
   n3qais SEQUENCE OF N3QAIList
}

N3QAIList ::= SEQUENCE {
   numQFIs INTEGER (0..255),
   --<inline/>
   --<length expr="@numQFIs"/>
   qfiList SEQUENCE OF OCTET STRING,
   numParams INTEGER (0..255),
   --<inline/>
   --<length expr="@numParams"/>
   paramsList SEQUENCE OF N3QAIParam
}

N3QAIParam ::= SEQUENCE {
   paramId INTEGER (0..255),
   --<is3GLength/>
   length INTEGER (1..255),
   --<inline/>
   contents CHOICE {
      --<selector element="paramId" value="1"/>
      fiveQI QOSFlowDescriptions,
      --<selector element="paramId" value="2"/>
      gfbrUL QOSFlowDescriptions,
      --<selector element="paramId" value="3"/>
      gfbrDL QOSFlowDescriptions,
      --<selector element="paramId" value="4"/>
      mfbrUL QOSFlowDescriptions,
      --<selector element="paramId" value="5"/>
      mfbrDL QOSFlowDescriptions,
      --<selector element="paramId" value="6"/>
      avgWindow QOSFlowDescriptions,
      --<selector element="paramId" value="7"/>
      resourceType AdditionalQoSInfo,
      --<selector element="paramId" value="8"/>
      priorityLevel AdditionalQoSInfo,
      --<selector element="paramId" value="9"/>
      packetDelayBudget AdditionalQoSInfo,
      --<selector element="paramId" value="10"/>
      packetErrRate AdditionalQoSInfo,
      --<selector element="paramId" value="11"/>
      maxDataBurstVol AdditionalQoSInfo,
      --<selector element="paramId" value="12"/>
      maxPktLossRateDL AdditionalQoSInfo,
      --<selector element="paramId" value="13"/>
      maxPktLossRateUL AdditionalQoSInfo,
      --<selector element="paramId" value="14"/>
      arp INTEGER (0..255),
      --<selector element="paramId" value="15"/>
      periodicity INTEGER (0..255)
   }
}

AdditionalQoSInfo ::= SEQUENCE {
   numParams INTEGER (0..255),
   --<inline/>
   --<length expr="@numParams"/>
   paramsList SEQUENCE OF AddlQoSParamsList
}

AddlQoSParamsList ::= SEQUENCE {
   paramId INTEGER (0..255),
   --<is3GLength/>
   length INTEGER (1..255),
   --<inline/>
   contents CHOICE {
      --<selector element="paramId" value="1"/>
      qosCharacteristics OCTET STRING (SIZE (10)),
      --<selector element="paramId" value="2"/>
      mfbrDL OCTET STRING (SIZE (3)),
      --<selector element="paramId" value="3"/>
      mfbrUL OCTET STRING (SIZE (3)),
      --<selector element="paramId" value="4"/>
      gfbrDL OCTET STRING (SIZE (3)),
      --<selector element="paramId" value="5"/>
      gfbrUL OCTET STRING (SIZE (3)),
      --<selector element="paramId" value="6"/>
      notificationCtrl NULL,
      --<selector element="paramId" value="7"/>
      maxPktLossRateDL OCTET STRING (SIZE (2)),
      --<selector element="paramId" value="8"/>
      maxPktLossRateUL OCTET STRING (SIZE (2))
   }
}

/* 9.11.4.37 - Non-3GPP delay budget - added in v18.4 */
Non3GDelayBudget ::= SEQUENCE {
   --<is3GLength bitFieldSize="16"/>
   length INTEGER (0..65535),
   --<is3GVarLenList lengthElem="length"/>
   delayBudgetList SEQUENCE OF DelayBudget
}

DelayBudget ::= SEQUENCE {
   value INTEGER (0..65535),
   spare INTEGER (0..63) DEFAULT 0,
   qfipi INTEGER (0..1),
   pfpi INTEGER (0..1),
   --<inline/>
   qfiInfo CHOICE {
      --<selector element="qfipi" value="0"/>
      absent NULL,
      --<selector element="qfipi" value="1"/>
      present SEQUENCE {
         numQFIs INTEGER (1..255),
         --<length expr="@.numQFIs"/>
         qfiList SEQUENCE OF OCTET STRING
      }
   },
   --<inline/>
   pktFilterList CHOICE {
      --<selector element="pfpi" value="0"/>
      absent NULL,
      --<selector element="pfpi" value="1"/>
      present PFCreateNew
   }
}

/* 9.11.4.38 - URSP rule enforcement reports - added in v18.6 */
URSPRuleEnforceReports ::= SEQUENCE {
   --<is3GLength/>
   length INTEGER (0..255),
   --<is3GVarLenList lengthElem="length"/>
   reports SEQUENCE OF URSPRuleReport
}

URSPRuleReport ::= SEQUENCE {
   numIdentifiers INTEGER (0..255),
   --<inline/>
   --<length expr="@numIdentifiers"/>
   connCapIdList SEQUENCE OF URSPRule -- Changed in v18.10
}

URSPRule ::= SEQUENCE { -- Added in v18.10
   --<is3GLength bitFieldSize="16"/>
   length INTEGER (0..65535),
   precedence INTEGER (0..255),
   trafficDesc TrafficDescriptorList,
   routeSelectionDesc RouteSelectionDescriptorList,
   addlIndications SEQUENCE {
      spare INTEGER (0..127) DEFAULT 0,
      ureri BOOLEAN
   }
}

TrafficDescriptorList ::=  SEQUENCE {
   --<is3GLength bitFieldSize="16"/>
   length INTEGER (1..65535),
   --<is3GVarLenList lengthElem="length"/>
   descriptors SEQUENCE OF TrafficDescriptor
}

RouteSelectionDescriptorList ::= SEQUENCE {
   --<is3GLength bitFieldSize="16"/>
   length INTEGER (0..65535),
   --<is3GVarLenList lengthElem="length"/>
   descriptors SEQUENCE OF RouteSelectionDescriptor
}

RouteSelectionDescriptor ::= SEQUENCE {
   --<is3GLength bitFieldSize="16"/>
   length INTEGER (0..65535),
   precedence INTEGER (0..255),
   --<is3GVarLenList lengthElem="length"/>
   contents SEQUENCE OF RouteSelectionDescriptorContents
}

RouteSelectionDescriptorContents ::= SEQUENCE {
   --<is3GLength bitFieldSize="16"/>
   length INTEGER (0..65535),
   --<is3GVarLenList lengthElem="length"/>
   components SEQUENCE OF RouteSelectionDescriptorComponent
}

RouteSelectionDescriptorComponent ::= SEQUENCE {
   typeId INTEGER (0..255),
   --<inline/>
   value CHOICE {
      --<selector element="typeId" value="1"/>
      sscMode SEQUENCE {
         spare INTEGER (0..15) DEFAULT 0,
         mode SSCMode
      },
      --<selector element="typeId" value="2"/>
      snssai SNSSAI,
      --<selector element="typeId" value="4"/>
      dnn DNNList,
      --<selector element="typeId" value="8"/>
      pduSession SEQUENCE {
         spare INTEGER (0..15) DEFAULT 0,
         session PDUSessionType
      },
      --<selector element="typeId" value="16"/>
      prefAccess SEQUENCE {
         spare INTEGER (0..15) DEFAULT 0,
         type AccessType
      },
      --<selector element="typeId" value="17"/>
      multiAccess NULL,
      --<selector element="typeId" value="32"/>
      nonSeamlessoffloadInd NULL,
      --<selector element="typeId" value="64"/>
      locCriteria LocationCriteria,
      --<selector element="typeId" value="128"/>
      timeWindow TimePeriod,
      --<selector element="typeId" value="129"/>
      proSeRelayOffloadInd NULL,
      --<selector element="typeId" value="130"/>
      pduSessionPairId PDUPairIds,
      --<selector element="typeId" value="131"/>
      rsn INTEGER (0..255),
      --<selector element="typeId" value="132"/>
      proSeMultiPathPref NULL
  }
}

LocationCriteria ::= SEQUENCE {
   --<is3GLength/>
   length INTEGER (0..255),
   --<is3GVarLenList lengthElem="length"/>
   areas SEQUENCE OF LocationArea
}

LocationArea ::= SEQUENCE {
   type INTEGER (0..255),
   --<inline/>
   contents CHOICE {
      --<selector element="type" value="1"/>
      eutraCellIdList EUTRACellIdList,
      --<selector element="type" value="2"/>
      nrCellIdList NRCellIdList,
      --<selector element="type" value="3"/>
      ranNodeIdList RANNodeIdList,
      --<selector element="type" value="4"/>
      taiList TrackingAreaIdentList
   }
}

EUTRACellIdList ::= SEQUENCE {
   numIds INTEGER (0..255),
   --<inline/>
   --<length expr="@numIds"/>
   eutraCellIds SEQUENCE OF EUTRACellId
}

EUTRACellId ::= SEQUENCE {
   plmnId MCCMNCPair,
   cellId BIT STRING (SIZE (28)),
   spare INTEGER (0..15) DEFAULT 0
}

NRCellIdList ::= SEQUENCE {
   numIds INTEGER (1..255),
   --<inline/>
   --<length expr="@numIds"/>
   nrCellIds SEQUENCE OF NRCellId
}

NRCellId ::= SEQUENCE {
   plmnId MCCMNCPair,
   cellId BIT STRING (SIZE (36)),
   spare INTEGER (0..15) DEFAULT 0
}

RANNodeIdList ::= SEQUENCE {
   numIds INTEGER (1..255),
   --<inline/>
   --<length expr="@numIds"/>
   ranNodeIds SEQUENCE OF RANNodeId
}

RANNodeId ::= SEQUENCE {
   plmnId MCCMNCPair,
   cellId BIT STRING (SIZE (32))
}

/* 9.11.4.39 - Protocol description - added in v18.6 */
ProtocolDescriptions ::= SEQUENCE {
   --<is3GLength bitFieldSize="16"/>
   length INTEGER (0..65535),
   --<is3GVarLenList lengthElem="length"/>
   descriptions SEQUENCE OF ProtocolDescription
}

ProtocolDescription ::= SEQUENCE {
   --<is3GLength bitFieldSize="16"/>
   length INTEGER (0..65535),
   qriRuleId INTEGER (0..255),
   spare INTEGER (0..3) DEFAULT 0,
   pilpi INTEGER (0..1),
   heipi INTEGER (0..1),
   transProtocol INTEGER (0..15),
   --<inline/>
   rtpHdrInfo CHOICE {
      --<selector element="heipi" value="0"/>
      absent NULL,
      --<selector element="heipi" value="1"/>
      hdrInfo SEQUENCE {
         type INTEGER (0..255),
         id INTEGER (0..255)
      }
   },
   --<inline/>
   rtpPayloadInfo CHOICE {
      --<selector element="pilpi" value="0"/>
      absent NULL,
      --<selector element="pilpi" value="1"/>
      payloadInfo RTPPayloadInfoList
   }
}

RTPPayloadInfoList ::= SEQUENCE {
   --<is3GLength bitFieldSize="16"/>
   length INTEGER (0..65535),
   --<is3GVarLenList lengthElem="length"/>
   info SEQUENCE OF RTPPayloadInfo
}

RTPPayloadInfo ::= SEQUENCE {
   format INTEGER (0..255),
   numTypes INTEGER (0..255),
   --<inline/>
   --<length expr="@numTypes"/>
   types SEQUENCE OF OCTET STRING
}

END
