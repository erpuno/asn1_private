/* 
Module for 3GPP TS 24.008 Messages, Releases 8 through 16.
Each message, being a standard L3 Message (see TS 24.007), has a standard
message header.  The header is factored out of each of the message types.
Current versions:
    v16.7.0
    v17.9.0
    v18.8.0
*/
TS24008Msgs DEFINITIONS AUTOMATIC TAGS ::=
BEGIN

IMPORTS 
NAS-PROTOCOL-CLASS, SecProtMsgHeader FROM TS24007L3

AC-Reference-Number, AccessPointName, AddnNetFeatureSupport, 
AddnUpdateParams, AddnUpdateType, AlertingPattern, 
AllowedActions, AttachResult, AttachType, 
AuthFailureParam, AuthParamAUTN, AuthParamRAND, AuthRespParam, 
AuthRespParamExt, AuxiliaryStates, BackupBearerCapability, 
BearerCapability, CC-Establishment, CMServiceType, 
CallControlCapabilities, CallState, CalledPartyBCDNumber, 
CallingPartyBCDNumber, Cause, CauseOfNoCLI, CiphKeySeqNum, 
CipheringAlgorithmType, CongestionLevel, ConnectedNumber, 
ConnectedSubaddress, ConnectivityType, DRXParameter, 
DaylightSavingTime, DetachType, DeviceProperties, 
E-UTRANInterRATInfoContainer, EmergencyNumberList, 
EnhancedNSAPIValue, ExtDRXParams, Facility, FacilityNetworkToMS, 
ForceToStandbyValue, GMMCauseValue, GPRSTimer, GPRSTimer2, GPRSTimer3, 
HighLayerCompatibility, IMEISVRequest, IdentityType2Value, IdentityTypeValue, 
IntegrityAlgorithmType, InterRATInfoContainer, KeypadFacilityInfo, 
LLCSAPIValue, LSAIdentifier, LinkedTI, LocAreaIdent, LocAreaIdent2, 
LocationUpdatingType, LowLayerCompatibility, MBMS-PCO, MBMSBearerCaps, 
MBMSContextStatus, MMTimer, MSNetworkCapability, MSNetFeatureSupport, 
MSRadioAccessCapability, MobileIdentity, 
MobileStationClassmark1, MobileStationClassmark2, 
MobileStationClassmark3, MsgAuthCode, NBIFOMContainer, NSAPIValue, 
NetCallCtrlCaps, NetFeatureSupp, NetworkName, NetResourceIdentContainer, 
NotificationIndicator, Notify, P-TMSISignature, 
P-TMSISignature2, P-TMSI-Type, PDAndSAPI, PDPContextStatus, 
PLMNList, PS-LCSCapbility, PacketDataProtoAddr, PacketFlowIdentValue, 
PartySubaddress, PriorityLevel, ProgressIndicator, ProtocolConfigOptions, 
QualityOfService, RadioPriority, RadioPriority2, ReattemptInd, 
RecallType, ReceiveNPDUNumberList, RedirectingPartyBCDNumber, RejectCauseValue, 
RepeatIndicator, RequestTypeValue, RequestedMSInfo, RetrieveReject, 
RoutingAreaIdent, RoutingAreaIdent2, SecProtMsgHeader, 
SMCause2Value, SMCauseValue, SMStatus, SSVersionIndicator, 
ServiceCategoryValue, ServiceType, Setup-Container, Signal, 
SM-NotificationIndicator, StartCC, StartDTMF, StartDTMFAck, 
StartDTMFReject, StreamIdentifierValue, SupportedCodecList, 
TDIValue, TFT, TMGI, TMSIStatus, TimeZone, TimeZoneAndTime, 
UpdateResult, UpdateType, UplinkDataStatus, 
UserPlaneIntegInd, UserUser, VoiceDomainPref, WLANOffloadAccept,
DcnID, PlmnCnID, Non3GPPNetPolicies, ExtProtoConfigOptions, ExtQualityOfService
FROM TS24008IES

UENetworkCapability
FROM TS24301IES
;

TS24008-IE-OBJECTSET NAS-PROTOCOL-CLASS ::= {
   obj-AuthenticationReject | obj-AuthenticationRequest | 
   obj-AuthenticationResponse | obj-AuthenticationFailure | 
   obj-CMReestabRequest | obj-CMServiceAccept | obj-CMServicePrompt | 
   obj-CMServiceReject | obj-CMServiceAbort | obj-Abort | 
   obj-CMServiceRequest | obj-IdentityRequest | obj-IdentityResponse | 
   obj-IMSIDetachInd | obj-LocUpdatingAccept | obj-LocUpdatingReject | 
   obj-LocUpdatingRequest | obj-MMInformation | obj-MMStatus | 
   obj-TMSIReallocCmd | obj-TMSIReallocCmplt | obj-MMNull | obj-Alerting | 
   obj-CallConfirmed | obj-CallProceeding | obj-CongestionControl | 
   obj-Connect | obj-ConnectAck | obj-Disconnect | obj-EmergencySetup | 
   obj-FacilityMsg | obj-Hold | obj-HoldAck | obj-HoldReject | obj-Modify | 
   obj-ModifyComplete | obj-ModifyReject | obj-Notify | obj-Progress | 
   obj-CC-Establishment | obj-CC-EstablishmentConfirmed | obj-Release | 
   obj-Recall | obj-ReleaseComplete | obj-Retrieve | obj-RetrieveAck | 
   obj-RetrieveReject | obj-Setup | obj-StartCC | obj-StartDTMF | 
   obj-StartDTMFAck | obj-StartDTMFReject | obj-Status | obj-StatusEnquiry | 
   obj-StopDTMF | obj-StopDTMFAck | obj-UserInfo | obj-AttachRequest | 
   obj-AttachAccept | obj-AttachComplete | obj-AttachReject | 
   obj-DetachRequest | obj-DetachAccept | obj-P-TMSIReallocCmd | 
   obj-P-TMSIReallocCmplt | obj-AuthAndCiphRequest | 
   obj-AuthAndCiphResponse | obj-AuthAndCiphFailure | obj-AuthAndCiphReject | 
   obj-GMMIdentityRequest | obj-GMMIdentityResponse | 
   obj-RoutingAreaUpdateRequest | obj-RoutingAreaUpdateAccept | 
   obj-RoutingAreaUpdateComplete | obj-RoutingAreaUpdateReject | 
   obj-GMMStatus | obj-GMMInformation | obj-ServiceRequest | 
   obj-ServiceAccept | obj-ServiceReject | obj-ActivatePDPCtxtReq | 
   obj-ActivatePDPCtxtAccept | obj-ActivatePDPCtxtReject | 
   obj-ActivateSecondaryPDPCtxtRqst | obj-ActivateSecondaryPDPCtxtAcc | 
   obj-ActivateSecondaryPDPCtxtRej | obj-RequestPDPCtxtAct | 
   obj-RequestPDPCtxtActRej | obj-ModifyPDPCtxtRqstNetToMS | 
   obj-ModifyPDPCtxtRqstMSToNet | obj-ModifyPDPCtxtAccMSToNet | 
   obj-ModifyPDPCtxtAccNetToMS | obj-ModifyPDPCtxtRej | 
   obj-DeactivatePDPCtxtReq | obj-DeactivatePDPCtxtAcc | 
   obj-RqstSecondaryPDPCtxtAct | obj-RqstSecondaryPDPCtxtActRej | 
   obj-SMStatus | obj-ActivateMBMSCtxtReq | obj-ActivateMBMSCtxtAcc | 
   obj-ActivateMBMSCtxtRej | obj-RequestMBMSCtxtAct | obj-RequestMBMSCtxtActRej,
   ...
}

PDU ::= SEQUENCE {
   -- L3 header, octet 1, bits 5 thru 8
   --<inline/>
   --<cDecSrcFname>TS24008MsgDec_PDU_l3HdrOpts.c</cDecSrcFname>
   l3HdrOpts CHOICE {
      skipInd INTEGER(0..15),
      --<inline/>
      --<selector element="protoDiscr" value="callCtrl,sessMgmt"/>
      transId SEQUENCE {
         flag BOOLEAN, 
         --<cEncSrcFname>TS24008MsgEnc_PDU_transId.c</cEncSrcFname>
         value INTEGER (0..255)
      }
   },
   protoDiscr   NAS-PROTOCOL-CLASS.&protoDiscr ({TS24008-IE-OBJECTSET}), 

   --<cEncSrcFname>TS24008MsgEnc_PDU_sendSeqNum.c</cEncSrcFname>
   --<cDecSrcFname>TS24008MsgDec_PDU_sendSeqNum.c</cDecSrcFname>
   sendSeqNum   INTEGER (0..3) OPTIONAL, 

   --<cEncSrcFname>TS24008MsgEnc_PDU_msgType.c</cEncSrcFname>
   --<cDecSrcFname>TS24008MsgDec_PDU_msgType.c</cDecSrcFname>
   msgType      NAS-PROTOCOL-CLASS.&msgType ({TS24008-IE-OBJECTSET}), 
   data         NAS-PROTOCOL-CLASS.&Value 
                   ({TS24008-IE-OBJECTSET}{@protoDiscr,@msgType})
}

/* 9.2.1 - Authentication reject */

mt-AuthenticationReject INTEGER ::= 17

obj-AuthenticationReject NAS-PROTOCOL-CLASS ::= { 
   ID mobMgmt, mt-AuthenticationReject
   TYPE NULL
}

/* 9.2.2 - Authentication request */

mt-AuthenticationRequest INTEGER ::= 18

obj-AuthenticationRequest NAS-PROTOCOL-CLASS ::= { 
   ID mobMgmt, mt-AuthenticationRequest
   TYPE AuthenticationRequest
}

AuthenticationRequest ::= SEQUENCE {
   spare INTEGER (0..15) DEFAULT 0,
   ciphKeySeqNum CiphKeySeqNum,
   authParamRAND AuthParamRAND,
   --<iei format="tlv">20</iei>
   authParamAUTN AuthParamAUTN OPTIONAL
}

/* 9.2.3 - Authentication response */

mt-AuthenticationResponse INTEGER ::= 20

obj-AuthenticationResponse NAS-PROTOCOL-CLASS ::= { 
   ID mobMgmt, mt-AuthenticationResponse
   TYPE AuthenticationResponse
}

AuthenticationResponse ::= SEQUENCE {
   respParam AuthRespParam,
   --<iei format="tlv">21</iei>
   respParamExt AuthRespParamExt OPTIONAL
}

/* 9.2.3a - Authentication failure */

mt-AuthenticationFailure INTEGER ::= 28

obj-AuthenticationFailure NAS-PROTOCOL-CLASS ::= { 
   ID mobMgmt, mt-AuthenticationFailure
   TYPE AuthenticationFailure
}

AuthenticationFailure ::= SEQUENCE {
   rejectCause RejectCauseValue,
   --<iei format="tlv">22</iei>
   failParam AuthFailureParam OPTIONAL
}

/* 9.2.4 - CM re-establishment request */

mt-CMReestabRequest INTEGER ::= 40

obj-CMReestabRequest NAS-PROTOCOL-CLASS ::= { 
   ID mobMgmt, mt-CMReestabRequest
   TYPE CMReestabRequest
}

CMReestabRequest ::= SEQUENCE {
   spare INTEGER(0..15) DEFAULT 0, 
   ciphKeySeqNum CiphKeySeqNum,
   mobileStationClassmark2 MobileStationClassmark2,
   mobileIdentity MobileIdentity,
   --<iei format="tv" length="6">13</iei>
   locAreaIdent LocAreaIdent OPTIONAL,
   ...,
   [[ 10:
   --<iei format="tv" length="1">D</iei>
   deviceProperties DeviceProperties OPTIONAL
   ]]
}
   

/* 9.2.5 - CM service accept */

mt-CMServiceAccept INTEGER ::= 33

obj-CMServiceAccept NAS-PROTOCOL-CLASS ::= { 
   ID mobMgmt, mt-CMServiceAccept
   TYPE NULL
}

/* 9.2.5a - CM service prompt */

mt-CMServicePrompt INTEGER ::= 37

obj-CMServicePrompt NAS-PROTOCOL-CLASS ::= { 
   ID mobMgmt, mt-CMServicePrompt
   TYPE CMServicePrompt
}

CMServicePrompt ::= SEQUENCE {
   pdAndSAPI PDAndSAPI
}

/* 9.2.6 - CM service reject */

mt-CMServiceReject INTEGER ::= 34

obj-CMServiceReject NAS-PROTOCOL-CLASS ::= { 
   ID mobMgmt, mt-CMServiceReject
   TYPE CMServiceReject
}

CMServiceReject ::= SEQUENCE {
   rejectCause RejectCauseValue, 
   ...,
   [[ 10:
   --<iei format="tlv">36</iei>
   t3246Value MMTimer OPTIONAL
   ]]
}

/* 9.2.7 - CM service abort */

mt-CMServiceAbort INTEGER ::= 35

obj-CMServiceAbort NAS-PROTOCOL-CLASS ::= { 
   ID mobMgmt, mt-CMServiceAbort
   TYPE NULL
}

/* 9.2.8 - Abort */

mt-Abort INTEGER ::= 41

obj-Abort NAS-PROTOCOL-CLASS ::= { 
   ID mobMgmt, mt-Abort
   TYPE Abort
}

Abort ::= SEQUENCE {
   rejectCause RejectCauseValue
}

/* 9.2.9 - CM service request */

mt-CMServiceRequest INTEGER ::= 36

obj-CMServiceRequest NAS-PROTOCOL-CLASS ::= { 
   ID mobMgmt, mt-CMServiceRequest
   TYPE CMServiceRequest
}

CMServiceRequest ::= SEQUENCE {
   ciphKeySeqNum CiphKeySeqNum,
   cmServiceType CMServiceType,
   mobileStationClassmark2 MobileStationClassmark2,
   mobileIdentity MobileIdentity,
   --<iei format="tv" length="1">8</iei>
   priorityLevel PriorityLevel OPTIONAL, 
   ...,
   [[ 10:
   --<iei format="tv" length="1">C</iei>
   addnUpdateParams AddnUpdateParams OPTIONAL, 
   --<iei format="tv" length="1">D</iei>
   deviceProperties DeviceProperties OPTIONAL
   ]]
}

/* 9.2.10 - Identity request */

mt-IdentityRequest INTEGER ::= 24

obj-IdentityRequest NAS-PROTOCOL-CLASS ::= { 
   ID mobMgmt, mt-IdentityRequest
   TYPE IdentityRequest
}

IdentityRequest ::= SEQUENCE {
   spare INTEGER (0..15) DEFAULT 0, 
   value IdentityTypeValue
}

/* 9.2.11 - Identity response */

mt-IdentityResponse INTEGER ::= 25

obj-IdentityResponse NAS-PROTOCOL-CLASS ::= { 
   ID mobMgmt, mt-IdentityResponse
   TYPE IdentityResponse
}

IdentityResponse ::= SEQUENCE {
   mobileIdentity MobileIdentity, 
   ...,
   [[ 11:
   --<iei format="tv" length="1">E</iei>
   p-TMSI-Type P-TMSI-Type OPTIONAL, 
   --<iei format="tlv">1B</iei>
   routingAreaId RoutingAreaIdent2 OPTIONAL,
   --<iei format="tlv">19</iei>
   pTMSISignature P-TMSISignature2 OPTIONAL
   ]]
}

/* 9.2.12 - IMSI detach indication */

mt-IMSIDetachInd INTEGER ::= 1

obj-IMSIDetachInd NAS-PROTOCOL-CLASS ::= { 
   ID mobMgmt, mt-IMSIDetachInd
   TYPE IMSIDetachInd
}

IMSIDetachInd ::= SEQUENCE {
   mobileStationClassmark1 MobileStationClassmark1,
   mobileIdentity MobileIdentity
}

/* 9.2.13 - Location updating accept */

mt-LocUpdatingAccept INTEGER ::= 2

obj-LocUpdatingAccept NAS-PROTOCOL-CLASS ::= { 
   ID mobMgmt, mt-LocUpdatingAccept
   TYPE LocUpdatingAccept
}

LocUpdatingAccept ::= SEQUENCE {
   locAreaIdent LocAreaIdent,
   --<iei format="tlv">17</iei>
   mobileIdentity MobileIdentity OPTIONAL,
   /* followOnProceed and ctsPermission contain no data, just IEI (tag) - 
      present flags are sufficient to indicate presence or absence */
   --<iei format="t">A1</iei>
   followOnProceed NULL OPTIONAL, 
   --<iei format="t">A2</iei>
   ctsPermission NULL OPTIONAL, 
   --<iei format="tlv">4A</iei>
   equivPLMNs PLMNList OPTIONAL,
   --<iei format="tlv">34</iei>
   emergNumList EmergencyNumberList OPTIONAL, 
   ...,
   [[ 10:
   --<iei format="tlv">35</iei>
   per-MS-T3212 GPRSTimer3 OPTIONAL
   ]],
   [[ 14:
   --<iei format="tv" length="1">0D</iei>
   non3GPPNetPolicies Non3GPPNetPolicies OPTIONAL
   ]]
}

/* 9.2.14 - Location updating reject */

mt-LocUpdatingReject INTEGER ::= 4

obj-LocUpdatingReject NAS-PROTOCOL-CLASS ::= { 
   ID mobMgmt, mt-LocUpdatingReject
   TYPE LocUpdatingReject
}

LocUpdatingReject ::= SEQUENCE {
   rejectCause RejectCauseValue, 
   ...,
   [[ 10:
   --<iei format="tlv">36</iei>
   t3246Value MMTimer OPTIONAL
   ]]
}

/* 9.2.15 - Location updating request */

mt-LocUpdatingRequest INTEGER ::= 8

obj-LocUpdatingRequest NAS-PROTOCOL-CLASS ::= { 
   ID mobMgmt, mt-LocUpdatingRequest
   TYPE LocUpdatingRequest
}

LocUpdatingRequest ::= SEQUENCE { 
   ciphKeySeqNum CiphKeySeqNum,
   locUpdatingType LocationUpdatingType,
   locAreaIdent LocAreaIdent,
   mobileStationClassmark1 MobileStationClassmark1,
   mobileIdentity MobileIdentity,
   --<iei format="tlv">33</iei>
   mobStatCmark4UMTS MobileStationClassmark2 OPTIONAL, 
   ...,
   [[ 9:
   --<iei format="tv" length="1">C</iei>
   addnUpdateParams AddnUpdateParams OPTIONAL
   ]],
   [[ 10:
   --<iei format="tv" length="1">D</iei>
   deviceProperties DeviceProperties OPTIONAL, 
   --<iei format="tv" length="1">E</iei>
   msNetFeatureSupport MSNetFeatureSupport OPTIONAL
   ]]

}

/* 9.2.15a - MM information */

mt-MMInformation INTEGER ::= 50

obj-MMInformation NAS-PROTOCOL-CLASS ::= { 
   ID mobMgmt, mt-MMInformation
   TYPE MMInformation
}

MMInformation ::= SEQUENCE { 
   --<iei format="tlv">43</iei>
   networkFullName NetworkName OPTIONAL,
   --<iei format="tlv">45</iei>
   networkShortName NetworkName OPTIONAL,
   --<iei format="tv" length="2">46</iei>
   localTimeZone TimeZone OPTIONAL,
   --<iei format="tv" length="8">47</iei>
   univAndLocalTimeZone TimeZoneAndTime OPTIONAL,
   --<iei format="tlv">48</iei>
   lsaIdentity LSAIdentifier OPTIONAL,
   --<iei format="tlv">49</iei>
   networkDaylightSavingTime DaylightSavingTime OPTIONAL
}

/* 9.2.16 - MM Status */

mt-MMStatus INTEGER ::= 49

obj-MMStatus NAS-PROTOCOL-CLASS ::= { 
   ID mobMgmt, mt-MMStatus
   TYPE MMStatus
}

MMStatus ::= SEQUENCE {
   rejectCause RejectCauseValue
}

/* 9.2.17 - TMSI reallocation command */

mt-TMSIReallocCmd INTEGER ::= 26

obj-TMSIReallocCmd NAS-PROTOCOL-CLASS ::= { 
   ID mobMgmt, mt-TMSIReallocCmd
   TYPE TMSIReallocCmd
}

TMSIReallocCmd ::= SEQUENCE {
   locAreaIdent LocAreaIdent,
   mobileIdentity MobileIdentity
}

/* 9.2.18 - TMSI reallocation complete (no data) */

mt-TMSIReallocCmplt INTEGER ::= 27

obj-TMSIReallocCmplt NAS-PROTOCOL-CLASS ::= { 
   ID mobMgmt, mt-TMSIReallocCmplt
   TYPE NULL
}

/* 9.2.19 - MM Null (no data) */

mt-MMNull INTEGER ::= 48

obj-MMNull NAS-PROTOCOL-CLASS ::= { 
   ID mobMgmt, mt-MMNull
   TYPE NULL
}

/* 9.3 - Messages for circuit-switched call control */

/* 9.3.1 - Alerting (this type includes the optional IE's for both the 
   network to mobile station and mobile station to network directions) */

mt-Alerting INTEGER ::= 1

obj-Alerting NAS-PROTOCOL-CLASS ::= { 
   ID callCtrl, mt-Alerting
   TYPE Alerting
}

Alerting ::= SEQUENCE {  
   --<iei format="tlv">1C</iei>
   facility Facility OPTIONAL,
   --<iei format="tlv">1E</iei>
   progressInd ProgressIndicator OPTIONAL,
   --<iei format="tlv">7E</iei>
   user-user UserUser OPTIONAL,
   --<iei format="tlv">7F</iei>
   ssVersion SSVersionIndicator OPTIONAL
}

/* 9.3.2 - Call confirmed */

mt-CallConfirmed INTEGER ::= 8

obj-CallConfirmed NAS-PROTOCOL-CLASS ::= { 
   ID callCtrl, mt-CallConfirmed
   TYPE CallConfirmed
}

CallConfirmed ::= SEQUENCE {
   --<iei format="tv" length="1">D</iei>
   repeatInd RepeatIndicator OPTIONAL,
   --<iei format="tlv">04</iei>
   bearerCap1 BearerCapability OPTIONAL,
   --<iei format="tlv">04</iei>
   bearerCap2 BearerCapability OPTIONAL,
   --<iei format="tlv">08</iei>
   cause Cause OPTIONAL,
   --<iei format="tlv">15</iei>
   callCtrlCap CallControlCapabilities OPTIONAL,
   --<iei format="tlv">2D</iei>
   streamId StreamIdentifierValue OPTIONAL,
   --<iei format="tlv">40</iei>
   supportedCodecs SupportedCodecList OPTIONAL
}

/* 9.3.3 - Call proceeding */

mt-CallProceeding INTEGER ::= 2

obj-CallProceeding NAS-PROTOCOL-CLASS ::= { 
   ID callCtrl, mt-CallProceeding
   TYPE CallProceeding
}

CallProceeding ::= SEQUENCE {
   --<iei format="tv" length="1">D</iei>
   repeatInd RepeatIndicator OPTIONAL,
   --<iei format="tlv">04</iei>
   bearerCap1 BearerCapability OPTIONAL,
   --<iei format="tlv">04</iei>
   bearerCap2 BearerCapability OPTIONAL,
   --<iei format="tlv">1C</iei>
   facility Facility OPTIONAL,
   --<iei format="tlv">1E</iei>
   progressInd ProgressIndicator OPTIONAL,
   --<iei format="tv" length="1">8</iei>
   priorityGranted PriorityLevel OPTIONAL,
   --<iei format="tlv">2F</iei>
   netCallCtrlCap NetCallCtrlCaps OPTIONAL
}

/* 9.3.4 - Congestion control */

mt-CongestionControl INTEGER ::= 57

obj-CongestionControl NAS-PROTOCOL-CLASS ::= { 
   ID callCtrl, mt-CongestionControl
   TYPE CongestionControl
}

CongestionControl ::= SEQUENCE {
   spare INTEGER (0..15) DEFAULT 0, 
   congestionLevel CongestionLevel,
   --<iei format="tlv">08</iei>
   cause Cause OPTIONAL
}

/* 9.3.5 - Connect (this type includes the optional IE's for both the 
   network to mobile station and mobile station to network directions) */

mt-Connect INTEGER ::= 7

obj-Connect NAS-PROTOCOL-CLASS ::= { 
   ID callCtrl, mt-Connect
   TYPE Connect
}

Connect ::= SEQUENCE {
   --<iei format="tlv">1C</iei>
   facility Facility OPTIONAL,
   --<iei format="tlv">1E</iei>
   progressInd ProgressIndicator OPTIONAL,
   --<iei format="tlv">4C</iei>
   connNumber ConnectedNumber OPTIONAL,
   --<iei format="tlv">4D</iei>
   connSubaddr ConnectedSubaddress OPTIONAL,
   --<iei format="tlv">7E</iei>
   user-user UserUser OPTIONAL, 
   --<iei format="tlv">7F</iei>
   ssVersion SSVersionIndicator OPTIONAL,
   --<iei format="tlv">2D</iei>
   streamId StreamIdentifierValue OPTIONAL
}

/* 9.3.6 - Connect acknowledge: message header only */

mt-ConnectAck INTEGER ::= 15

obj-ConnectAck NAS-PROTOCOL-CLASS ::= { 
   ID callCtrl, mt-ConnectAck
   TYPE NULL
}

/* 9.3.7 Disconnect (this type includes the optional IE's for both the 
   network to mobile station and mobile station to network directions) */

mt-Disconnect INTEGER ::= 37

obj-Disconnect NAS-PROTOCOL-CLASS ::= { 
   ID callCtrl, mt-Disconnect
   TYPE Disconnect
}

Disconnect ::= SEQUENCE {
   cause Cause,
   --<iei format="tlv">1C</iei>
   facility Facility OPTIONAL,
   --<iei format="tlv">1E</iei>
   progressInd ProgressIndicator OPTIONAL,
   --<iei format="tlv">7E</iei>
   user-user UserUser OPTIONAL,
   --<iei format="tlv">7B</iei>
   allowedActions AllowedActions OPTIONAL, 
   --<iei format="tlv">7F</iei>
   ssVersion SSVersionIndicator OPTIONAL
}

/* 9.3.8 - Emergency setup */

mt-EmergencySetup INTEGER ::= 14

obj-EmergencySetup NAS-PROTOCOL-CLASS ::= { 
   ID callCtrl, mt-EmergencySetup
   TYPE EmergencySetup
}

EmergencySetup ::= SEQUENCE {   
   --<iei format="tlv">04</iei>
   bearerCap BearerCapability OPTIONAL,
   --<iei format="tlv">2D</iei>
   streamId StreamIdentifierValue OPTIONAL,
   --<iei format="tlv">40</iei>
   supportedCodecs SupportedCodecList OPTIONAL,
   --<iei format="tlv">2E</iei>
   emergencyCat ServiceCategoryValue OPTIONAL
}

/* 9.3.9 - Facility (this type includes the optional IE's for both the 
   network to mobile station and mobile station to network directions) */

mt-FacilityMsg INTEGER ::= 58

obj-FacilityMsg NAS-PROTOCOL-CLASS ::= { 
   ID callCtrl, mt-FacilityMsg
   TYPE FacilityMsg
}

FacilityMsg ::= SEQUENCE {
   facility Facility,
   --<iei format="tlv">7F</iei>
   ssVersion SSVersionIndicator OPTIONAL
}

/* 9.3.10 - Hold : message header only */

mt-Hold INTEGER ::= 24

obj-Hold NAS-PROTOCOL-CLASS ::= { 
   ID callCtrl, mt-Hold
   TYPE NULL
}

/* 9.3.11 - Hold Acknowledge : message header only */

mt-HoldAck INTEGER ::= 25

obj-HoldAck NAS-PROTOCOL-CLASS ::= { 
   ID callCtrl, mt-HoldAck
   TYPE NULL
}

/* 9.3.12 - Hold Reject */

mt-HoldReject INTEGER ::= 26

obj-HoldReject NAS-PROTOCOL-CLASS ::= { 
   ID callCtrl, mt-HoldReject
   TYPE Cause
}

/* 9.3.13 Modify */

mt-Modify INTEGER ::= 23

obj-Modify NAS-PROTOCOL-CLASS ::= { 
   ID callCtrl, mt-Modify
   TYPE Modify
}

Modify ::= SEQUENCE {
   bearerCap BearerCapability,
   --<iei format="tlv">7C</iei>
   lowLayerComp LowLayerCompatibility OPTIONAL,
   --<iei format="tlv">7D</iei>
   highLayerComp HighLayerCompatibility OPTIONAL,
   --<iei format="t" length="1">A3</iei>
   revCallSetupDirection NULL OPTIONAL,
   --<iei format="t" length="1">A4</iei>
   netInitServUpgrdInd NULL OPTIONAL
}

/* 9.3.14 - Modify complete */

mt-ModifyComplete INTEGER ::= 31

obj-ModifyComplete NAS-PROTOCOL-CLASS ::= { 
   ID callCtrl, mt-ModifyComplete
   TYPE ModifyComplete
}

ModifyComplete ::= SEQUENCE {
   bearerCap BearerCapability,
   --<iei format="tlv">7C</iei>
   lowLayerComp LowLayerCompatibility OPTIONAL,
   --<iei format="tlv">7D</iei>
   highLayerComp HighLayerCompatibility OPTIONAL,
   --<iei format="t" length="1">A3</iei>
   revCallSetupDirection NULL OPTIONAL
}

/* 9.3.15 - Modify reject */

mt-ModifyReject INTEGER ::= 19

obj-ModifyReject NAS-PROTOCOL-CLASS ::= { 
   ID callCtrl, mt-ModifyReject
   TYPE ModifyReject
}

ModifyReject ::= SEQUENCE {
   bearerCap BearerCapability,
   cause Cause,
   --<iei format="tlv">7C</iei>
   lowLayerComp LowLayerCompatibility OPTIONAL,
   --<iei format="tlv">7D</iei>
   highLayerComp HighLayerCompatibility OPTIONAL
}

/* 9.3.16 - Notify */

mt-Notify INTEGER ::= 62

obj-Notify NAS-PROTOCOL-CLASS ::= { 
   ID callCtrl, mt-Notify
   TYPE NotificationIndicator
}

/* 9.3.17 - Progress */

mt-Progress INTEGER ::= 3

obj-Progress NAS-PROTOCOL-CLASS ::= { 
   ID callCtrl, mt-Progress
   TYPE Progress
}

Progress ::= SEQUENCE {
   progressInd ProgressIndicator,
   --<iei format="tlv">7E</iei>
   user-user UserUser OPTIONAL
}

/* 9.3.17a - CC-Establishment $(CCBS)$ */

mt-CC-Establishment INTEGER ::= 4

obj-CC-Establishment NAS-PROTOCOL-CLASS ::= { 
   ID callCtrl, mt-CC-Establishment
   TYPE Setup-Container
}

/* 9.3.17b - CC-Establishment confirmed $(CCBS)$ */

mt-CC-EstablishmentConfirmed INTEGER ::= 6

obj-CC-EstablishmentConfirmed NAS-PROTOCOL-CLASS ::= { 
   ID callCtrl, mt-CC-EstablishmentConfirmed
   TYPE CC-EstablishmentConfirmed
}

CC-EstablishmentConfirmed ::= SEQUENCE {
   --<iei format="tv" length="1">D</iei>
   repeatInd RepeatIndicator OPTIONAL,
   --<iei format="tlv">04</iei>
   bearerCap1 BearerCapability OPTIONAL,
   --<iei format="tlv">04</iei>
   bearerCap2 BearerCapability OPTIONAL,
   --<iei format="tlv">08</iei>
   cause Cause OPTIONAL,
   --<iei format="tlv">40</iei>
   supportedCodecs SupportedCodecList OPTIONAL
}

/* 9.3.18 - Release (this type includes the optional IE's for both the 
   network to mobile station and mobile station to network directions) */

mt-Release INTEGER ::= 45

obj-Release NAS-PROTOCOL-CLASS ::= { 
   ID callCtrl, mt-Release
   TYPE Release
}

Release ::= SEQUENCE {
   --<iei format="tlv">08</iei>
   cause Cause OPTIONAL,
   --<iei format="tlv">08</iei>
   secondCause Cause OPTIONAL,
   --<iei format="tlv">1C</iei>
   facility Facility OPTIONAL,
   --<iei format="tlv">7E</iei>
   user-user UserUser OPTIONAL,
   --<iei format="tlv">7F</iei>
   ssVersion SSVersionIndicator OPTIONAL
}

/* 9.3.18a - Recall $(CCBS)$ */

mt-Recall INTEGER ::= 11

obj-Recall NAS-PROTOCOL-CLASS ::= { 
   ID callCtrl, mt-Recall
   TYPE Recall
}

Recall ::= SEQUENCE {
   recallType RecallType,
   facility Facility
}

/* 9.3.19 - Release complete (this type includes the optional IE's for 
both the network to mobile station and mobile station to network directions) */

mt-ReleaseComplete INTEGER ::= 42

obj-ReleaseComplete NAS-PROTOCOL-CLASS ::= { 
   ID callCtrl, mt-ReleaseComplete
   TYPE ReleaseComplete
}

ReleaseComplete ::= SEQUENCE {
   --<iei format="tlv">08</iei>
   cause Cause OPTIONAL,
   --<iei format="tlv">1C</iei>
   facility Facility OPTIONAL,
   --<iei format="tlv">7E</iei>
   user-user UserUser OPTIONAL,
   --<iei format="tlv">7F</iei>
   ssVersion SSVersionIndicator OPTIONAL
}

/* 9.3.20 - Retrieve: message header only */

mt-Retrieve INTEGER ::= 28

obj-Retrieve NAS-PROTOCOL-CLASS ::= { 
   ID callCtrl, mt-Retrieve
   TYPE NULL
}

/* 9.3.21 - Retrieve Acknowledge: message header only */

mt-RetrieveAck INTEGER ::= 29

obj-RetrieveAck NAS-PROTOCOL-CLASS ::= { 
   ID callCtrl, mt-RetrieveAck
   TYPE NULL
}

/* 9.3.22 - Retrieve Reject */

mt-RetrieveReject INTEGER ::= 30

obj-RetrieveReject NAS-PROTOCOL-CLASS ::= { 
   ID callCtrl, mt-RetrieveReject
   TYPE Cause
}

/* 9.3.23.1 - Setup (this type contains optional IE's for both mobile 
terminated and mobile originated call establishment) */

mt-Setup INTEGER ::= 5

obj-Setup NAS-PROTOCOL-CLASS ::= { 
   ID callCtrl, mt-Setup
   TYPE Setup
}

Setup ::= SEQUENCE {
   --<iei format="tv" length="1">D</iei>
   bcRepeatInd RepeatIndicator OPTIONAL,
   --<iei format="tlv">04</iei>
   bearerCapability1 BearerCapability OPTIONAL,
   --<iei format="tlv">04</iei>
   bearerCapability2 BearerCapability OPTIONAL,
   --<iei format="tlv">1C</iei>
   facility Facility OPTIONAL,
   --<iei format="tlv">1E</iei>
   progressInd ProgressIndicator OPTIONAL,
   --<iei format="tv" length="2">34</iei>
   signal Signal OPTIONAL,
   --<iei format="tlv">5C</iei>
   callingPartyNumber CallingPartyBCDNumber OPTIONAL,
   --<iei format="tlv">5D</iei>
   callingPartySubaddress PartySubaddress OPTIONAL,
   --<iei format="tlv">5E</iei>
   calledPartyNumber CalledPartyBCDNumber OPTIONAL,
   --<iei format="tlv">6D</iei>
   calledPartySubaddress PartySubaddress OPTIONAL,
   --<iei format="tlv">74</iei>
   redirectingPartyNumber RedirectingPartyBCDNumber OPTIONAL,
   --<iei format="tlv">75</iei>
   redirectingPartySubaddress PartySubaddress OPTIONAL,
   --<iei format="tv" length="1">D</iei>
   llcRepeatInd RepeatIndicator OPTIONAL,
   --<iei format="tlv">7C</iei>
   lowLayerCompat1 LowLayerCompatibility OPTIONAL,
   --<iei format="tlv">7C</iei>
   lowLayerCompat2 LowLayerCompatibility OPTIONAL,
   --<iei format="tv" length="1">D</iei>
   hlcRepeatInd RepeatIndicator OPTIONAL,
   --<iei format="tlv">7D</iei>
   highLayerCompat1 HighLayerCompatibility OPTIONAL,
   --<iei format="tlv">7D</iei>
   highLayerCompat2 HighLayerCompatibility OPTIONAL,
   --<iei format="tlv">7E</iei>
   userUser UserUser OPTIONAL,

   -- the following IE's are present in mobile terminated only
   --<iei format="tv" length="1">8</iei>
   priorityLevel PriorityLevel OPTIONAL,
   --<iei format="tlv">19</iei>
   alertingPattern AlertingPattern OPTIONAL,
   --<iei format="tlv">2F</iei>
   netCallCtrlCaps NetCallCtrlCaps OPTIONAL,
   --<iei format="tlv">3A</iei>
   causeOfNoCLI CauseOfNoCLI OPTIONAL,
   --<iei format="tlv">41</iei>
   backupBearerCapability BackupBearerCapability OPTIONAL, 

   -- the following IE's are present in mobile originated only
   --<iei format="tlv">7F</iei>
   ssVersion SSVersionIndicator OPTIONAL,
   --<iei format="t" length="1">A1</iei>
   clirSuppression NULL OPTIONAL, 
   --<iei format="t" length="1">A2</iei>
   clirInvocation NULL OPTIONAL, 
   --<iei format="tlv">15</iei>
   callCtrlCap CallControlCapabilities OPTIONAL,
   --<iei format="tlv">1D</iei>
   facilityAdvRecallAlign Facility OPTIONAL,
   --<iei format="tlv">1B</iei>
   facilityRecallAlignNotEssential Facility OPTIONAL,
   --<iei format="tlv">2D</iei>
   streamId StreamIdentifierValue OPTIONAL,
   --<iei format="tlv">40</iei>
   supportedCodecs SupportedCodecList OPTIONAL,
   --<iei format="t">A3</iei>
   redial NULL OPTIONAL
}

/* 9.3.23a Start CC $(CCBS)$ */

mt-StartCC INTEGER ::= 9

obj-StartCC NAS-PROTOCOL-CLASS ::= { 
   ID callCtrl, mt-StartCC
   TYPE StartCC
}

StartCC ::= SEQUENCE {
   --<iei format="tlv">15</iei>
   ccCapabilities CallControlCapabilities OPTIONAL
}

/* 9.3.24 - Start DTMF */

mt-StartDTMF INTEGER ::= 53

obj-StartDTMF NAS-PROTOCOL-CLASS ::= { 
   ID callCtrl, mt-StartDTMF
   TYPE StartDTMF
}

StartDTMF ::= SEQUENCE {
   --<iei format="tv" length="2">2C</iei>
   keypadFacility KeypadFacilityInfo OPTIONAL
}

/* 9.3.25 Start DTMF Acknowledge */

mt-StartDTMFAck INTEGER ::= 54

obj-StartDTMFAck NAS-PROTOCOL-CLASS ::= { 
   ID callCtrl, mt-StartDTMFAck
   TYPE StartDTMFAck
}

StartDTMFAck ::= StartDTMF

/* 9.3.26 Start DTMF reject */

mt-StartDTMFReject INTEGER ::= 55

obj-StartDTMFReject NAS-PROTOCOL-CLASS ::= { 
   ID callCtrl, mt-StartDTMFReject
   TYPE Cause
}

/* 9.3.27 Status */

mt-Status INTEGER ::= 61

obj-Status NAS-PROTOCOL-CLASS ::= { 
   ID callCtrl, mt-Status
   TYPE Status
}

Status ::= SEQUENCE {
   cause Cause,
   callState CallState,
   --<iei format="tlv">24</iei>
   auxStates AuxiliaryStates OPTIONAL
}

/* 9.3.28 Status enquiry: header only */

mt-StatusEnquiry INTEGER ::= 52

obj-StatusEnquiry NAS-PROTOCOL-CLASS ::= { 
   ID callCtrl, mt-StatusEnquiry
   TYPE NULL
}

/* 9.3.29 Stop DTMF: header only */

mt-StopDTMF INTEGER ::= 49

obj-StopDTMF NAS-PROTOCOL-CLASS ::= { 
   ID callCtrl, mt-StopDTMF
   TYPE NULL
}

/* 9.3.30 Stop DTMF acknowledge: header only */

mt-StopDTMFAck INTEGER ::= 50

obj-StopDTMFAck NAS-PROTOCOL-CLASS ::= { 
   ID callCtrl, mt-StopDTMFAck
   TYPE NULL
}

/* 9.3.31 User information */

mt-UserInfo INTEGER ::= 16

obj-UserInfo NAS-PROTOCOL-CLASS ::= { 
   ID callCtrl, mt-UserInfo
   TYPE UserInfo
}

UserInfo ::= SEQUENCE {
   userUser UserUser,
   /* 10.5.4.19 More Data is IEI only */   
   --<iei format="t">A0</iei>
   moreData NULL OPTIONAL
}

/* 9.4 - GPRS Mobility Management Messages */

/* 9.4.1 Attach request */

mt-AttachRequest INTEGER ::= 1

obj-AttachRequest NAS-PROTOCOL-CLASS ::= { 
   ID gprsMobMgmt, mt-AttachRequest
   TYPE AttachRequest
}

AttachRequest ::= SEQUENCE {
   msNetCapability MSNetworkCapability,
   gprsCiphKeySeq CiphKeySeqNum,
   attachType AttachType,
   drxParameter DRXParameter,
   pTMSIOrIMSI MobileIdentity,
   oldRoutingAreaId RoutingAreaIdent,
   msRACapability MSRadioAccessCapability,
   --<iei format="tv" length="4">19</iei>
   oldPTMSISignature P-TMSISignature OPTIONAL,
   --<iei format="tv" length="2">17</iei>
   reqREADYTimerValue GPRSTimer OPTIONAL,
   --<iei format="tv" length="1">9</iei>
   tmsiStatus TMSIStatus OPTIONAL,
   --<iei format="tlv">33</iei>
   psLCSCap PS-LCSCapbility OPTIONAL,
   --<iei format="tlv">11</iei>
   msClassmark2 MobileStationClassmark2 OPTIONAL,
   --<iei format="tlv">20</iei>
   msClassmark3 MobileStationClassmark3 OPTIONAL,
   --<iei format="tlv">40</iei>
   supportedCodecs SupportedCodecList OPTIONAL,
   --<iei format="tlv">58</iei>
   ueNetCap UENetworkCapability OPTIONAL,
   --<iei format="tlv">1A</iei>
   addnMobileId MobileIdentity OPTIONAL,
   --<iei format="tlv">1B</iei>
   addnOldRoutingAreaId RoutingAreaIdent2 OPTIONAL,
   ...,
   [[ 9:
   --<iei format="tlv">5D</iei>
   voiceDomainPref VoiceDomainPref OPTIONAL
   ]], 
   [[ 10:
   --<iei format="tv" length="1">D</iei>
   deviceProperties DeviceProperties OPTIONAL,
   --<iei format="tv" length="1">E</iei>
   p-TMSI-Type P-TMSI-Type OPTIONAL, 
   --<iei format="tv" length="1">C</iei>
   msNetFeatureSupport MSNetFeatureSupport OPTIONAL, 
   --<iei format="tlv">14</iei>
   oldLocAreaIdent LocAreaIdent2 OPTIONAL
   ]],
   [[ 11:
   --<iei format="tv" length="1">F</iei>
   addnUpdateType AddnUpdateType OPTIONAL, 
   --<iei format="tlv">10</iei>
   tmsiBasedNRICont NetResourceIdentContainer OPTIONAL
   ]], 
   [[ 12:
   --<iei format="tlv">6A</iei>
   t3324Value GPRSTimer2 OPTIONAL, 
   --<iei format="tlv">39</iei>
   t3312ExtValue GPRSTimer3 OPTIONAL
   ]], 
   [[ 13:
   --<iei format="tlv">6E</iei>
   extDRXParams ExtDRXParams OPTIONAL
   ]]
}

/* 9.4.2 Attach accept */

mt-AttachAccept INTEGER ::= 2

obj-AttachAccept NAS-PROTOCOL-CLASS ::= { 
   ID gprsMobMgmt, mt-AttachAccept
   TYPE AttachAccept
}

AttachAccept ::= SEQUENCE {
   forceToStandby ForceToStandbyValue,
   attachResult AttachResult,
   periodicRAUpdateTimer GPRSTimer,
   radioPriForTOM8 RadioPriority2,
   radioPriForSMS RadioPriority,
   routingAreaIdent RoutingAreaIdent,
   --<iei format="tv" length="4">19</iei>
   pTMSISignature P-TMSISignature OPTIONAL,
   --<iei format="tv" length="2">17</iei>
   negotiatedREADYTimerValue GPRSTimer OPTIONAL,
   --<iei format="tlv">18</iei>
   allocatedPTMSI MobileIdentity OPTIONAL,
   --<iei format="tlv">23</iei>
   msIdentity MobileIdentity OPTIONAL,
   --<iei format="tv" length="2">25</iei>
   gmmCause GMMCauseValue OPTIONAL,
   --<iei format="tlv">2A</iei>
   t3302Value GPRSTimer2 OPTIONAL,
   --<iei format="t">8C</iei>
   cellNotification NULL OPTIONAL,
   --<iei format="tlv">4A</iei>
   equivalentPLMNs PLMNList OPTIONAL,
   --<iei format="tv" length="1">B</iei>
   netFeatureSupport NetFeatureSupp OPTIONAL,
   --<iei format="tlv">34</iei>
   emergencyNumList EmergencyNumberList OPTIONAL,
   --<iei format="tv" length="1">A</iei>
   requestedMSInfo RequestedMSInfo OPTIONAL,
   --<iei format="tlv">37</iei>
   t3319Value GPRSTimer2 OPTIONAL,
   --<iei format="tlv">38</iei>
   t3323Value GPRSTimer2 OPTIONAL, 
   ...,
   [[ 10:
   --<iei format="tlv">39</iei>
   t3312Value GPRSTimer3 OPTIONAL
   ]],
   [[ 11:
   --<iei format="tlv">66</iei>
   addnNetFeatureSupport AddnNetFeatureSupport OPTIONAL
   ]],
   [[ 12:
   --<iei format="tlv">6A</iei>
   t3324Value GPRSTimer2 OPTIONAL
   ]],
   [[ 13:
   --<iei format="tlv">6E</iei>
   extDRXParams ExtDRXParams OPTIONAL, 
   --<iei format="tv" length="1">C</iei>
   userPlaneIntegInd UserPlaneIntegInd OPTIONAL, 
   --<iei format="tlv">31</iei>
   replayMSNetCapability MSNetworkCapability OPTIONAL, 
   --<iei format="tlv">33</iei>
   replayMSRadioAccessCap MSRadioAccessCapability OPTIONAL
   ]],
   [[ 14:
   --<iei format="tlv">65</iei>
   dcnId DcnID OPTIONAL,
   --<iei format="tlv">63</iei>
   plmnCnId PlmnCnID OPTIONAL,
   --<iei format="tv" length="1">0D</iei>
   non3GPPNetPolicies Non3GPPNetPolicies OPTIONAL -- added in v14.4.0
   ]]
}

/* 9.4.3 Attach complete */

mt-AttachComplete INTEGER ::= 3

obj-AttachComplete NAS-PROTOCOL-CLASS ::= { 
   ID gprsMobMgmt, mt-AttachComplete
   TYPE AttachComplete
}

AttachComplete ::= SEQUENCE {
   --<iei format="tlv">27</iei>
   erRATInfoContainer InterRATInfoContainer OPTIONAL,
   --<iei format="tlv">2B</iei>
   eUTRANInterRATInfoContainer E-UTRANInterRATInfoContainer OPTIONAL
}

/* 9.4.4 Attach reject */

mt-AttachReject INTEGER ::= 4

obj-AttachReject NAS-PROTOCOL-CLASS ::= { 
   ID gprsMobMgmt, mt-AttachReject
   TYPE AttachReject
}

AttachReject ::= SEQUENCE {
   gmmCause GMMCauseValue,
   --<iei format="tlv">2A</iei>
   t3302Value GPRSTimer2 OPTIONAL, 
   ...,
   [[ 10:
   --<iei format="tlv">3A</iei>
   t3346Value GPRSTimer2 OPTIONAL
   ]]
}

/* 9.4.5 Detach request (this type contains optional IE's for both mobile 
terminated and mobile originated detach) */

mt-DetachRequest INTEGER ::= 5

obj-DetachRequest NAS-PROTOCOL-CLASS ::= { 
   ID gprsMobMgmt, mt-DetachRequest
   TYPE DetachRequest
}

DetachRequest ::= SEQUENCE {
   detachType DetachType,
   forceToStandby ForceToStandbyValue, -- spare in mobile originated

   -- this IE is used in mobile terminated only
   --<iei format="tv" length="2">25</iei>
   gmmCause GMMCauseValue OPTIONAL, 

   -- thess IE's are used in mobile originated only
   --<iei format="tlv">18</iei>
   pTMSI MobileIdentity OPTIONAL,
   --<iei format="tlv">19</iei>
   pTMSISignature P-TMSISignature2 OPTIONAL
}

/* 9.4.6 Detach accept (note: a custom encoder and decoder are required 
for this message type because the force-to-standby field which is a 
required field is present in the mobile originated case but not in 
the mobile terminated case. */

mt-DetachAccept INTEGER ::= 6

obj-DetachAccept NAS-PROTOCOL-CLASS ::= { 
   ID gprsMobMgmt, mt-DetachAccept
   TYPE DetachAccept
}

DetachAccept ::= SEQUENCE {
   -- present flag must be set to false in mobile terminated case and 
   -- custom encoder will simply omit the value
   forceToStandby ForceToStandbyValue OPTIONAL
}

/* 9.4.7 P-TMSI reallocation command */

mt-P-TMSIReallocCmd INTEGER ::= 16

obj-P-TMSIReallocCmd NAS-PROTOCOL-CLASS ::= { 
   ID gprsMobMgmt, mt-P-TMSIReallocCmd
   TYPE P-TMSIReallocCmd
}

P-TMSIReallocCmd ::= SEQUENCE {
   allocatedPTMSI MobileIdentity,
   routingAreaIdent RoutingAreaIdent,
   forceToStandby ForceToStandbyValue,
   spare INTEGER (0..15) DEFAULT 0, 
   --<iei format="tv" length="4">19</iei>
   pTMSISignature P-TMSISignature OPTIONAL,
   ...,
   [[ 14:
   --<iei format="tlv">65</iei>
   dcnId DcnID OPTIONAL
   ]]
}

/* 9.4.8 P-TMSI reallocation complete */

mt-P-TMSIReallocCmplt INTEGER ::= 17

obj-P-TMSIReallocCmplt NAS-PROTOCOL-CLASS ::= { 
   ID gprsMobMgmt, mt-P-TMSIReallocCmplt
   TYPE NULL
}

/* 9.4.9 Authentication and ciphering request */

mt-AuthAndCiphRequest INTEGER ::= 18

obj-AuthAndCiphRequest NAS-PROTOCOL-CLASS ::= { 
   ID gprsMobMgmt, mt-AuthAndCiphRequest
   TYPE AuthAndCiphRequest
}

AuthAndCiphRequest ::= SEQUENCE {
   cipheringAlgorithm CipheringAlgorithmType,
   imeisvRequest IMEISVRequest,
   forceToStandby ForceToStandbyValue,
   acRefNumber AC-Reference-Number,
   --<iei format="tv" length="17">21</iei>
   authParamRAND AuthParamRAND OPTIONAL,
   --<iei format="tv" length="1">8</iei>
   ciphKeySeqNum CiphKeySeqNum OPTIONAL,
   --<iei format="tlv">28</iei>
   authParamAUTN AuthParamAUTN OPTIONAL, 
   ...,
   [[ 13:
   --<iei format="tlv">31</iei>
   replayMSNetCapability MSNetworkCapability OPTIONAL, 
   --<iei format="tv" length="1">9</iei>
   integAlgorithm IntegrityAlgorithmType OPTIONAL, 
   --<iei format="tlv">43</iei>
   msgAuthCode MsgAuthCode OPTIONAL,
   --<iei format="tlv">33</iei>
   replayMSRadioAccessCap MSRadioAccessCapability OPTIONAL
   ]]
}

/* 9.4.10 Authentication and ciphering response */

mt-AuthAndCiphResponse INTEGER ::= 19

obj-AuthAndCiphResponse NAS-PROTOCOL-CLASS ::= { 
   ID gprsMobMgmt, mt-AuthAndCiphResponse
   TYPE AuthAndCiphResponse
}

AuthAndCiphResponse ::= SEQUENCE {
   spare INTEGER (0..15) DEFAULT 0, 
   acRefNumber AC-Reference-Number,
   --<iei format="tv" length="5">22</iei>
   authRespParam AuthRespParam OPTIONAL,
   --<iei format="tlv">23</iei>
   imeisv MobileIdentity OPTIONAL, 
   --<iei format="tlv">29</iei>
   authRespParamExt AuthRespParamExt OPTIONAL, 
   ...,
   [[ 13:
   --<iei format="tlv">43</iei>
   msgAuthCode MsgAuthCode OPTIONAL
   ]]
}

/* 9.4.10a Authentication and Ciphering Failure */

mt-AuthAndCiphFailure INTEGER ::= 28

obj-AuthAndCiphFailure NAS-PROTOCOL-CLASS ::= { 
   ID gprsMobMgmt, mt-AuthAndCiphFailure
   TYPE AuthAndCiphFailure
}

AuthAndCiphFailure ::= SEQUENCE {
   gmmCause GMMCauseValue,
   --<iei format="tlv">30</iei>
   authFailureParam AuthFailureParam OPTIONAL
} 

/* 9.4.11 Authentication and ciphering reject */

mt-AuthAndCiphReject INTEGER ::= 20

obj-AuthAndCiphReject NAS-PROTOCOL-CLASS ::= { 
   ID gprsMobMgmt, mt-AuthAndCiphReject
   TYPE NULL
}

/* 9.4.12 - Identity request */

mt-GMMIdentityRequest INTEGER ::= 21

obj-GMMIdentityRequest NAS-PROTOCOL-CLASS ::= { 
   ID gprsMobMgmt, mt-GMMIdentityRequest
   TYPE GMMIdentityRequest
}

GMMIdentityRequest ::= SEQUENCE {
   forceToStandby ForceToStandbyValue, 
   identityType IdentityType2Value
}

/* 9.4.13 - Identity response */

mt-GMMIdentityResponse INTEGER ::= 22

obj-GMMIdentityResponse NAS-PROTOCOL-CLASS ::= { 
   ID gprsMobMgmt, mt-GMMIdentityResponse
   TYPE GMMIdentityResponse
}

GMMIdentityResponse ::= SEQUENCE {
   mobileIdentity MobileIdentity
}

/* 9.4.14 - Routing area update request */

mt-RoutingAreaUpdateRequest INTEGER ::= 8

obj-RoutingAreaUpdateRequest NAS-PROTOCOL-CLASS ::= { 
   ID gprsMobMgmt, mt-RoutingAreaUpdateRequest
   TYPE RoutingAreaUpdateRequest
}

RoutingAreaUpdateRequest ::= SEQUENCE {
   gprsCiphKeySeq CiphKeySeqNum,
   updateType UpdateType,
   oldRoutingAreaId RoutingAreaIdent,
   msRACapability MSRadioAccessCapability,
   --<iei format="tv" length="4">19</iei>
   oldPTMSISignature P-TMSISignature OPTIONAL,
   --<iei format="tv" length="2">17</iei>
   reqREADYTimerValue GPRSTimer OPTIONAL,
   --<iei format="tv" length="3">27</iei>
   drxParameter DRXParameter OPTIONAL,
   --<iei format="tv" length="1">9</iei>
   tmsiStatus TMSIStatus OPTIONAL,
   --<iei format="tlv">18</iei>
   pTMSI MobileIdentity OPTIONAL,
   --<iei format="tlv">31</iei>
   msNetCapability MSNetworkCapability OPTIONAL,
   --<iei format="tlv">32</iei>
   pdpContextStatus PDPContextStatus OPTIONAL,
   --<iei format="tlv">33</iei>
   psLCSCap PS-LCSCapbility OPTIONAL,
   --<iei format="tlv">35</iei>
   mbmsContextStatus MBMSContextStatus OPTIONAL,
   --<iei format="tlv">58</iei>
   ueNetCap UENetworkCapability OPTIONAL,
   --<iei format="tlv">1A</iei>
   addnMobileId MobileIdentity OPTIONAL,
   --<iei format="tlv">1B</iei>
   addnOldRoutingAreaId RoutingAreaIdent2 OPTIONAL,
   --<iei format="tlv">11</iei>
   msClassmark2 MobileStationClassmark2 OPTIONAL,
   --<iei format="tlv">20</iei>
   msClassmark3 MobileStationClassmark3 OPTIONAL,
   --<iei format="tlv">40</iei>
   supportedCodecs SupportedCodecList OPTIONAL, 
   ...,
   [[ 9:
   --<iei format="tlv">5D</iei>
   voiceDomainPref VoiceDomainPref OPTIONAL
   ]], 
   [[ 10:
   --<iei format="tv" length="1">E</iei>
   p-TMSI-Type P-TMSI-Type OPTIONAL, 
   --<iei format="tv" length="1">D</iei>
   deviceProperties DeviceProperties OPTIONAL,
   --<iei format="tv" length="1">C</iei>
   msNetFeatureSupport MSNetFeatureSupport OPTIONAL, 
   --<iei format="tlv">14</iei>
   oldLocAreaIdent LocAreaIdent2 OPTIONAL
   ]],
   [[ 11:
   --<iei format="tv" length="1">F</iei>
   addnUpdateType AddnUpdateType OPTIONAL, 
   --<iei format="tlv">10</iei>
   tmsiBasedNRICont NetResourceIdentContainer OPTIONAL
   ]],
   [[ 12:
   --<iei format="tlv">6A</iei>
   t3324Value GPRSTimer2 OPTIONAL, 
   --<iei format="tlv">39</iei>
   t3312ExtValue GPRSTimer3 OPTIONAL
   ]], 
   [[ 13:
   --<iei format="tlv">6E</iei>
   extDRXParams ExtDRXParams OPTIONAL
   ]]
}

/* 9.4.15 - Routing area update accept */

mt-RoutingAreaUpdateAccept INTEGER ::= 9

obj-RoutingAreaUpdateAccept NAS-PROTOCOL-CLASS ::= { 
   ID gprsMobMgmt, mt-RoutingAreaUpdateAccept
   TYPE RoutingAreaUpdateAccept
}

RoutingAreaUpdateAccept ::= SEQUENCE {
   updateResult UpdateResult,
   forceToStandby ForceToStandbyValue,
   periodicRAUpdateTimer GPRSTimer,
   routingAreaIdent RoutingAreaIdent,
   --<iei format="tv" length="4">19</iei>
   pTMSISignature P-TMSISignature OPTIONAL,
   --<iei format="tlv">18</iei>
   allocatedPTMSI MobileIdentity OPTIONAL,
   --<iei format="tlv">23</iei>
   msIdentity MobileIdentity OPTIONAL,
   --<iei format="tlv">26</iei>
   receiveNPDUNumberList ReceiveNPDUNumberList OPTIONAL,
   --<iei format="tv" length="2">17</iei>
   negotiatedREADYTimerValue GPRSTimer OPTIONAL,
   --<iei format="tv" length="2">25</iei>
   gmmCause GMMCauseValue OPTIONAL,
   --<iei format="tlv">2A</iei>
   t3302Value GPRSTimer2 OPTIONAL,
   --<iei format="t">8C</iei>
   cellNotification NULL OPTIONAL, 
   --<iei format="tlv">4A</iei>
   equivalentPLMNs PLMNList OPTIONAL,
   --<iei format="tlv">32</iei>
   pdpContextStatus PDPContextStatus OPTIONAL,
   --<iei format="tv" length="1">B</iei>
   netFeatureSupport NetFeatureSupp OPTIONAL,
   --<iei format="tlv">34</iei>
   emergencyNumList EmergencyNumberList OPTIONAL,
   --<iei format="tlv">35</iei>
   mbmsContextStatus MBMSContextStatus OPTIONAL,
   --<iei format="tv" length="1">A</iei>
   requestedMSInfo RequestedMSInfo OPTIONAL,
   --<iei format="tlv">37</iei>
   t3319Value GPRSTimer2 OPTIONAL,
   --<iei format="tlv">38</iei>
   t3323Value GPRSTimer2 OPTIONAL, 
   ...,
   [[ 10:
   --<iei format="tlv">39</iei>
   t3312Value GPRSTimer3 OPTIONAL
   ]], 
   [[ 11:
   --<iei format="tlv">66</iei>
   addnNetFeatureSupport AddnNetFeatureSupport OPTIONAL
   ]],
   [[ 12:
   --<iei format="tlv">6A</iei>
   t3324Value GPRSTimer2 OPTIONAL
   ]],
   [[ 13:
   --<iei format="tlv">6E</iei>
   extDRXParams ExtDRXParams OPTIONAL,
   --<iei format="tv" length="1">C</iei>
   userPlaneIntegInd UserPlaneIntegInd OPTIONAL, 
   --<iei format="tlv">31</iei>
   replayMSNetCapability MSNetworkCapability OPTIONAL, 
   --<iei format="tlv">33</iei>
   replayMSRadioAccessCap MSRadioAccessCapability OPTIONAL
   ]],
   [[ 14:
   --<iei format="tlv">65</iei>
   dcnId DcnID OPTIONAL,
   --<iei format="tlv">63</iei>
   plmnCnId PlmnCnID OPTIONAL,
   --<iei format="tv" length="1">0D</iei>
   non3GPPNetPolicies Non3GPPNetPolicies OPTIONAL
   ]]
}

/* 9.4.16 - Routing area update complete */

mt-RoutingAreaUpdateComplete INTEGER ::= 10

obj-RoutingAreaUpdateComplete NAS-PROTOCOL-CLASS ::= { 
   ID gprsMobMgmt, mt-RoutingAreaUpdateComplete
   TYPE RoutingAreaUpdateComplete
}

RoutingAreaUpdateComplete ::= SEQUENCE {
   --<iei format="tlv">26</iei>
   receiveNPDUNumberList ReceiveNPDUNumberList OPTIONAL,
   --<iei format="tlv">27</iei>
   interRATInfoContainer InterRATInfoContainer OPTIONAL,
   --<iei format="tlv">2B</iei>
   eUTRANInterRATInfoContainer E-UTRANInterRATInfoContainer OPTIONAL
}

/* 9.4.17 - Routing area update reject */

mt-RoutingAreaUpdateReject INTEGER ::= 11

obj-RoutingAreaUpdateReject NAS-PROTOCOL-CLASS ::= { 
   ID gprsMobMgmt, mt-RoutingAreaUpdateReject
   TYPE RoutingAreaUpdateReject
}

RoutingAreaUpdateReject ::= SEQUENCE {
   gmmCause GMMCauseValue,
   spare INTEGER (0..15) DEFAULT 0,
   forceToStandby ForceToStandbyValue,
   --<iei format="tlv">2A</iei>
   gprsTimer2 GPRSTimer2 OPTIONAL, 
   ...,
   [[ 10:
   --<iei format="tlv">3A</iei>
   t3346Value GPRSTimer2 OPTIONAL
   ]]
}

/* 9.4.18 - GMM Status */

mt-GMMStatus INTEGER ::= 32

obj-GMMStatus NAS-PROTOCOL-CLASS ::= { 
   ID gprsMobMgmt, mt-GMMStatus
   TYPE GMMCauseValue
}

/* 9.4.19 - GMM Information */

mt-GMMInformation INTEGER ::= 33

obj-GMMInformation NAS-PROTOCOL-CLASS ::= { 
   ID gprsMobMgmt, mt-GMMInformation
   TYPE GMMInformation
}

GMMInformation ::= SEQUENCE {
   --<iei format="tlv">43</iei>
   fullNetName NetworkName OPTIONAL,
   --<iei format="tlv">45</iei>
   shortNetName NetworkName OPTIONAL,
   --<iei format="tv" length="2">46</iei>
   localTimeZone TimeZone OPTIONAL,
   --<iei format="tv" length="8">47</iei>
   universalAndLocalTimeZone TimeZoneAndTime OPTIONAL,
   --<iei format="tlv">48</iei>
   lsaIdentity LSAIdentifier OPTIONAL,
   --<iei format="tlv">49</iei>
   networkDST DaylightSavingTime OPTIONAL
}

/* 9.4.20 - GMM Service Request (UMTS only) */

mt-ServiceRequest INTEGER ::= 12

obj-ServiceRequest NAS-PROTOCOL-CLASS ::= { 
   ID gprsMobMgmt, mt-ServiceRequest
   TYPE ServiceRequest
}

ServiceRequest ::= SEQUENCE {
   serviceType ServiceType,
   ciphKeySeqNum CiphKeySeqNum,
   mobileIdentity MobileIdentity,
   --<iei format="tlv">32</iei>
   pdpContextStatus PDPContextStatus OPTIONAL,
   --<iei format="tlv">35</iei>
   mbmsContextStatus MBMSContextStatus OPTIONAL,
   --<iei format="tlv">36</iei>
   uplinkDataStatus UplinkDataStatus OPTIONAL, 
   ...,
   [[ 10:
   --<iei format="tv" length="1">D</iei>
   deviceProperties DeviceProperties OPTIONAL
   ]]
}

/* 9.4.21 - GMM Service Accept (UMTS only) */

mt-ServiceAccept INTEGER ::= 13

obj-ServiceAccept NAS-PROTOCOL-CLASS ::= { 
   ID gprsMobMgmt, mt-ServiceAccept
   TYPE ServiceAccept
}

ServiceAccept ::= SEQUENCE {
   --<iei format="tlv">32</iei>
   pdpContextStatus PDPContextStatus OPTIONAL,
   --<iei format="tlv">35</iei>
   mbmsContextStatus MBMSContextStatus OPTIONAL
}

/* 9.4.22 - Service Reject (UMTS only) */

mt-ServiceReject INTEGER ::= 14

obj-ServiceReject NAS-PROTOCOL-CLASS ::= { 
   ID gprsMobMgmt, mt-ServiceReject
   TYPE ServiceReject
}

ServiceReject ::= SEQUENCE {
   gmmCause GMMCauseValue, 
   ...,
   [[ 10:
   --<iei format="tlv">3A</iei>
   t3346Value GPRSTimer2 OPTIONAL
   ]]
}

/* 9.5 - GPRS Session Management Messages */

/* 9.5.1 - GSM Activate PDP Context Request */

mt-ActivatePDPCtxtReq INTEGER ::= 65

obj-ActivatePDPCtxtReq NAS-PROTOCOL-CLASS ::= { 
   ID sessMgmt, mt-ActivatePDPCtxtReq
   TYPE ActivatePDPCtxtReq
}

ActivatePDPCtxtReq ::= SEQUENCE {
   requestedNSAPI NSAPIValue,
   requestedLLCSAPI LLCSAPIValue,
   requestedQOS QualityOfService,
   requestedPDPAddr PacketDataProtoAddr,
   --<iei format="tlv">28</iei>
   accessPointName AccessPointName OPTIONAL,
   --<iei format="tlv">27</iei>
   protocolConfigOptions ProtocolConfigOptions OPTIONAL,
   --<iei format="tv" length="1">A</iei>
   requestType RequestTypeValue OPTIONAL, 
   ...,
   [[ 10:
   --<iei format="tv" length="1">C</iei>
   deviceProperties DeviceProperties OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.2 - GSM Activate PDP Context Accept */

mt-ActivatePDPCtxtAccept INTEGER ::= 66

obj-ActivatePDPCtxtAccept NAS-PROTOCOL-CLASS ::= { 
   ID sessMgmt, mt-ActivatePDPCtxtAccept
   TYPE ActivatePDPCtxtAccept
}

ActivatePDPCtxtAccept ::= SEQUENCE {
   negotiatedLLCSAPI LLCSAPIValue,
   negotiatedQOS QualityOfService,
   spare INTEGER (0..15) DEFAULT 0, 
   radioPriority RadioPriority,
   --<iei format="tlv">2B</iei>
   pdpAddress PacketDataProtoAddr OPTIONAL,
   --<iei format="tlv">27</iei>
   protocolConfigOptions ProtocolConfigOptions OPTIONAL,
   --<iei format="tlv">34</iei>
   packetFlowIdent PacketFlowIdentValue OPTIONAL,
   --<iei format="tlv">39</iei>
   smCause SMCause2Value OPTIONAL, 
   ...,
   [[ 10:
   --<iei format="tv" length="1">B</iei>
   connectivityType ConnectivityType OPTIONAL
   ]],
   [[ 12:
   --<iei format="tv" length="1">C</iei>
   wlanOffloadInd WLANOffloadAccept OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.3 - GSM Activate PDP Context Reject */

mt-ActivatePDPCtxtReject INTEGER ::= 67

obj-ActivatePDPCtxtReject NAS-PROTOCOL-CLASS ::= { 
   ID sessMgmt, mt-ActivatePDPCtxtReject
   TYPE ActivatePDPCtxtReject
}

ActivatePDPCtxtReject ::= SEQUENCE {
   smCause SMCauseValue,
   --<iei format="tlv">27</iei>
   protocolConfigOptions ProtocolConfigOptions OPTIONAL, 
   ...,
   [[ 10:
   --<iei format="tlv">37</iei>
   t3396Value GPRSTimer3 OPTIONAL
   ]],
   [[ 12:
   --<iei format="tlv">6B</iei>
   reattemptInd ReattemptInd OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]]
}

/* 9.5.4 - GSM Activate Secondary PDP Context Request */

mt-ActivateSecondaryPDPCtxtRqst INTEGER ::= 77

obj-ActivateSecondaryPDPCtxtRqst NAS-PROTOCOL-CLASS ::= { 
   ID sessMgmt, mt-ActivateSecondaryPDPCtxtRqst
   TYPE ActivateSecondaryPDPCtxtRqst
}

ActivateSecondaryPDPCtxtRqst ::= SEQUENCE {
   requestedNSAPI NSAPIValue,
   requestedLLCSAPI LLCSAPIValue,
   requestedQOS QualityOfService,
   linkedTI LinkedTI,
   --<iei format="tlv">36</iei>
   trafficFlowTemplate TFT OPTIONAL,
   --<iei format="tlv">27</iei>
   protocolConfigOptions ProtocolConfigOptions OPTIONAL, 
   ...,
   [[ 10:
   --<iei format="tv" length="1">C</iei>
   deviceProperties DeviceProperties OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.5 - GSM Activate Secondary PDP Context Accept */

mt-ActivateSecondaryPDPCtxtAcc INTEGER ::= 78

obj-ActivateSecondaryPDPCtxtAcc NAS-PROTOCOL-CLASS ::= { 
   ID sessMgmt, mt-ActivateSecondaryPDPCtxtAcc
   TYPE ActivateSecondaryPDPCtxtAcc
}

ActivateSecondaryPDPCtxtAcc ::= SEQUENCE {
   negotiatedLLCSAPI LLCSAPIValue,
   negotiatedQOS QualityOfService,
   spare INTEGER (0..15) DEFAULT 0, 
   radioPriority RadioPriority,
   --<iei format="tlv">34</iei>
   packetFlowIdent PacketFlowIdentValue OPTIONAL,
   --<iei format="tlv">27</iei>
   protocolConfigOptions ProtocolConfigOptions OPTIONAL,
   ...,
   [[ 12:
   --<iei format="tv" length="1">C</iei>
   wlanOffloadInd WLANOffloadAccept OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.6 - GSM Activate Secondary PDP Context Reject */

mt-ActivateSecondaryPDPCtxtRej INTEGER ::= 79

obj-ActivateSecondaryPDPCtxtRej NAS-PROTOCOL-CLASS ::= { 
   ID sessMgmt, mt-ActivateSecondaryPDPCtxtRej
   TYPE ActivateSecondaryPDPCtxtRej
}

ActivateSecondaryPDPCtxtRej ::= ActivatePDPCtxtReject

/* 9.5.7 - GSM Request PDP Context Activation */

mt-RequestPDPCtxtAct INTEGER ::= 68

obj-RequestPDPCtxtAct NAS-PROTOCOL-CLASS ::= { 
   ID sessMgmt, mt-RequestPDPCtxtAct
   TYPE RequestPDPCtxtAct
}

RequestPDPCtxtAct ::= SEQUENCE {
   offeredPDPAddress PacketDataProtoAddr,
   --<iei format="tlv">28</iei>
   accessPointName AccessPointName OPTIONAL,
   --<iei format="tlv">27</iei>
   protocolConfigOptions ProtocolConfigOptions OPTIONAL,
   ...,
   [[ 13:
   --<iei format="tlv">33</iei>
   nbifomContainer NBIFOMContainer OPTIONAL
   ]],
   [[ 14:
   --<iei format="tlv-e">7B</iei>
   extProtoConfigOptions ExtProtoConfigOptions OPTIONAL
   ]]
}

/* 9.5.8 - GSM Request PDP Context Activation Reject */

mt-RequestPDPCtxtActRej INTEGER ::= 69

obj-RequestPDPCtxtActRej NAS-PROTOCOL-CLASS ::= { 
   ID sessMgmt, mt-RequestPDPCtxtActRej
   TYPE RequestPDPCtxtActRej
}

RequestPDPCtxtActRej ::= SEQUENCE {
   smCause SMCauseValue,
   --<iei format="tlv">27</iei>
   protocolConfigOptions ProtocolConfigOptions OPTIONAL, 
   ...,
   [[ 13:
   --<iei format="tlv">33</iei>
   nbifomContainer NBIFOMContainer OPTIONAL
   ]],
   [[ 14:
   --<iei format="tlv-e">7B</iei>
   extProtoConfigOptions ExtProtoConfigOptions OPTIONAL
   ]]
}

/* 9.5.9 - GSM Modify PDP Context Request (Network to MS Direction) */

mt-ModifyPDPCtxtRqstNetToMS INTEGER ::= 72

obj-ModifyPDPCtxtRqstNetToMS NAS-PROTOCOL-CLASS ::= { 
   ID sessMgmt, mt-ModifyPDPCtxtRqstNetToMS
   TYPE ModifyPDPCtxtRqstNetToMS
}

ModifyPDPCtxtRqstNetToMS ::= SEQUENCE {
   spare INTEGER (0..15) DEFAULT 0, 
   radioPriority RadioPriority,
   requestedLLCSAPI LLCSAPIValue,
   newQOS QualityOfService,
   --<iei format="tlv">2B</iei>
   pdpAddress PacketDataProtoAddr OPTIONAL,
   --<iei format="tlv">34</iei>
   packetFlowIdent PacketFlowIdentValue OPTIONAL,
   --<iei format="tlv">27</iei>
   protocolConfigOptions ProtocolConfigOptions OPTIONAL,
   --<iei format="tlv">36</iei>
   trafficFlowTemplate TFT OPTIONAL,
   ...,
   [[ 12:
   --<iei format="tv" length="1">C</iei>
   wlanOffloadInd WLANOffloadAccept OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.10 - GSM Modify PDP Context Request (MS to Network Direction) */

mt-ModifyPDPCtxtRqstMSToNet INTEGER ::= 74

obj-ModifyPDPCtxtRqstMSToNet NAS-PROTOCOL-CLASS ::= { 
   ID sessMgmt, mt-ModifyPDPCtxtRqstMSToNet
   TYPE ModifyPDPCtxtRqstMSToNet
}

ModifyPDPCtxtRqstMSToNet ::= SEQUENCE {
   --<iei format="tv" length="2">32</iei>
   requestedLLCSAPI LLCSAPIValue OPTIONAL,
   --<iei format="tlv">30</iei>
   requestedNewQOS QualityOfService OPTIONAL,
   --<iei format="tlv">31</iei>
   newTFT TFT OPTIONAL,
   --<iei format="tlv">27</iei>
   protocolConfigOptions ProtocolConfigOptions OPTIONAL, 
   ...,
   [[ 10:
   --<iei format="tv" length="1">C</iei>
   deviceProperties DeviceProperties OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.11 - GSM Modify PDP Context Accept (MS to Network Direction) */

mt-ModifyPDPCtxtAccMSToNet INTEGER ::= 73

obj-ModifyPDPCtxtAccMSToNet NAS-PROTOCOL-CLASS ::= { 
   ID sessMgmt, mt-ModifyPDPCtxtAccMSToNet
   TYPE ModifyPDPCtxtAccMSToNet
}

ModifyPDPCtxtAccMSToNet ::= SEQUENCE {
   --<iei format="tlv">27</iei>
   protocolConfigOptions ProtocolConfigOptions OPTIONAL,
   ...,
   [[ 13:
   --<iei format="tlv">33</iei>
   nbifomContainer NBIFOMContainer OPTIONAL
   ]],
   [[ 14:
   --<iei format="tlv-e">7B</iei>
   extProtoConfigOptions ExtProtoConfigOptions OPTIONAL
   ]]
}

/* 9.5.12 - GSM Modify PDP Context Accept (Network to MS Direction) */

mt-ModifyPDPCtxtAccNetToMS INTEGER ::= 75

obj-ModifyPDPCtxtAccNetToMS NAS-PROTOCOL-CLASS ::= { 
   ID sessMgmt, mt-ModifyPDPCtxtAccNetToMS
   TYPE ModifyPDPCtxtAccNetToMS
}

ModifyPDPCtxtAccNetToMS ::= SEQUENCE {
   --<iei format="tlv">30</iei>
   negotiatedQOS QualityOfService OPTIONAL,
   --<iei format="tv" length="2">32</iei>
   negotiatedLLCSAPI LLCSAPIValue OPTIONAL,
   --<iei format="tv" length="1">8</iei>
   newRadioPriority RadioPriority OPTIONAL,
   --<iei format="tlv">34</iei>
   packetFlowIdent PacketFlowIdentValue OPTIONAL,
   --<iei format="tlv">27</iei>
   protocolConfigOptions ProtocolConfigOptions OPTIONAL, 
   ..., 
   [[ 12:
   --<iei format="tv" length="1">C</iei>
   wlanOffloadInd WLANOffloadAccept OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.13 - GSM Modify PDP Context Reject */

mt-ModifyPDPCtxtRej INTEGER ::= 76

obj-ModifyPDPCtxtRej NAS-PROTOCOL-CLASS ::= { 
   ID sessMgmt, mt-ModifyPDPCtxtRej
   TYPE ModifyPDPCtxtRej
}

ModifyPDPCtxtRej ::= ActivatePDPCtxtReject

/* 9.5.14 - GSM Deactivate PDP Context Request */

mt-DeactivatePDPCtxtReq INTEGER ::= 70

obj-DeactivatePDPCtxtReq NAS-PROTOCOL-CLASS ::= { 
   ID sessMgmt, mt-DeactivatePDPCtxtReq
   TYPE DeactivatePDPCtxtReq
}

DeactivatePDPCtxtReq ::= SEQUENCE {
   smCause SMCauseValue,
   --<iei format="tv" length="1">9</iei>
   tearDownIndicator TDIValue OPTIONAL,
   --<iei format="tlv">27</iei>
   protocolConfigOptions ProtocolConfigOptions OPTIONAL,
   --<iei format="tlv">35</iei>
   mbmsPCO MBMS-PCO OPTIONAL, 
   ...,
   [[ 11:
   --<iei format="tlv">37</iei>
   t3396Value GPRSTimer3 OPTIONAL
   ]],
   [[ 12:
   --<iei format="tv" length="1">C</iei>
   wlanOffloadInd WLANOffloadAccept OPTIONAL
   ]],
   [[ 14:
   --<iei format="tlv-e">7B</iei>
   extProtoConfigOptions ExtProtoConfigOptions OPTIONAL
   ]]
}

/* 9.5.15 - GSM Deactivate PDP Context Accept */

mt-DeactivatePDPCtxtAcc INTEGER ::= 71

obj-DeactivatePDPCtxtAcc NAS-PROTOCOL-CLASS ::= { 
   ID sessMgmt, mt-DeactivatePDPCtxtAcc
   TYPE DeactivatePDPCtxtAcc
}

DeactivatePDPCtxtAcc ::= SEQUENCE {
   --<iei format="tlv">27</iei>
   protocolConfigOptions ProtocolConfigOptions OPTIONAL,
   --<iei format="tlv">35</iei>
   mbmsPCO MBMS-PCO OPTIONAL,
   ...,
   [[ 14:
   --<iei format="tlv-e">7B</iei>
   extProtoConfigOptions ExtProtoConfigOptions OPTIONAL
   ]]
}

/* 9.5.15a - GSM Request Secondary PDP Context Activation */

mt-RqstSecondaryPDPCtxtAct INTEGER ::= 91

obj-RqstSecondaryPDPCtxtAct NAS-PROTOCOL-CLASS ::= { 
   ID sessMgmt, mt-RqstSecondaryPDPCtxtAct
   TYPE RqstSecondaryPDPCtxtAct
}

RqstSecondaryPDPCtxtAct ::= SEQUENCE {
   requiredQOS QualityOfService,
   linkedTI LinkedTI,
   --<iei format="tlv">36</iei>
   trafficFlowTemplate TFT OPTIONAL,
   --<iei format="tlv">27</iei>
   protocolConfigOptions ProtocolConfigOptions OPTIONAL, 
   ...,
   [[ 12:
   --<iei format="tv" length="1">C</iei>
   wlanOffloadInd WLANOffloadAccept OPTIONAL
   ]],
   [[ 13:
   --<iei format="tlv">33</iei>
   nbifomContainer NBIFOMContainer OPTIONAL
   ]],
   [[ 14:
   --<iei format="tlv-e">7B</iei>
   extProtoConfigOptions ExtProtoConfigOptions OPTIONAL
   ]],
   [[ 15:
   --<iei format="tlv">5C</iei>
   extQOS ExtQualityOfService OPTIONAL
   ]]
}

/* 9.5.15b - GSM Request Secondary PDP Context Activation Reject */

mt-RqstSecondaryPDPCtxtActRej INTEGER ::= 92

obj-RqstSecondaryPDPCtxtActRej NAS-PROTOCOL-CLASS ::= { 
   ID sessMgmt, mt-RqstSecondaryPDPCtxtActRej
   TYPE RqstSecondaryPDPCtxtActRej
}

RqstSecondaryPDPCtxtActRej ::= SEQUENCE {
   smCause SMCauseValue,
   --<iei format="tlv">27</iei>
   protocolConfigOptions ProtocolConfigOptions OPTIONAL, 
   ...,
   [[ 13:
   --<iei format="tlv">33</iei>
   nbifomContainer NBIFOMContainer OPTIONAL
   ]],
   [[ 14:
   --<iei format="tlv-e">7B</iei>
   extProtoConfigOptions ExtProtoConfigOptions OPTIONAL
   ]]
}

/* 9.5.16a - Notification */

mt-Notification INTEGER ::= 93

obj-Notification NAS-PROTOCOL-CLASS ::= { 
   ID sessMgmt, mt-Notification
   TYPE SM-NotificationIndicator
}

/* 9.5.21 - GSM SM Status */

mt-SMStatus INTEGER ::= 85

obj-SMStatus NAS-PROTOCOL-CLASS ::= { 
   ID sessMgmt, mt-SMStatus
   TYPE SMCauseValue
}

/* 9.5.22 - GSM Activate MBMS Context Request */

mt-ActivateMBMSCtxtReq INTEGER ::= 86

obj-ActivateMBMSCtxtReq NAS-PROTOCOL-CLASS ::= { 
   ID sessMgmt, mt-ActivateMBMSCtxtReq
   TYPE ActivateMBMSCtxtReq
}

ActivateMBMSCtxtReq ::= SEQUENCE {
   requestedMBMSNSAPI EnhancedNSAPIValue,
   requestedLLCSAPI LLCSAPIValue,
   supportedMBMSBearerCaps MBMSBearerCaps,
   requestedMulticastAddr PacketDataProtoAddr,
   accessPointName AccessPointName,
   --<iei format="tlv">35</iei>
   mbmsPCO MBMS-PCO OPTIONAL, 
   ...,
   [[ 10:
   --<iei format="tv" length="1">C</iei>
   deviceProperties DeviceProperties OPTIONAL
   ]]
}

/* 9.5.23 - GSM Activate MBMS Context Accept */

mt-ActivateMBMSCtxtAcc INTEGER ::= 87

obj-ActivateMBMSCtxtAcc NAS-PROTOCOL-CLASS ::= { 
   ID sessMgmt, mt-ActivateMBMSCtxtAcc
   TYPE ActivateMBMSCtxtAcc
}

ActivateMBMSCtxtAcc ::= SEQUENCE {
   tmgi TMGI, /* Temporary mobile group identity */
   negotiatedLLCSAPI LLCSAPIValue,
   --<iei format="tlv">35</iei>
   mbmsPCO MBMS-PCO OPTIONAL
}

/* 9.5.24 - GSM Activate MBMS Context Reject */

mt-ActivateMBMSCtxtRej INTEGER ::= 88

obj-ActivateMBMSCtxtRej NAS-PROTOCOL-CLASS ::= { 
   ID sessMgmt, mt-ActivateMBMSCtxtRej
   TYPE ActivateMBMSCtxtRej
}

ActivateMBMSCtxtRej ::= SEQUENCE {
   smCause SMCauseValue,
   --<iei format="tlv">35</iei>
   mbmsPCO MBMS-PCO OPTIONAL, 
   ...,
   [[ 10:
   --<iei format="tlv">37</iei>
   t3396Value GPRSTimer3 OPTIONAL
   ]],
   [[ 13:
   --<iei format="tlv">6B</iei>
   reattemptInd ReattemptInd OPTIONAL
   ]]
}

/* 9.5.25 - GSM Request MBMS Context Activation */

mt-RequestMBMSCtxtAct INTEGER ::= 89

obj-RequestMBMSCtxtAct NAS-PROTOCOL-CLASS ::= { 
   ID sessMgmt, mt-RequestMBMSCtxtAct
   TYPE RequestMBMSCtxtAct
}

RequestMBMSCtxtAct ::= SEQUENCE {
   linkedNSAPI NSAPIValue,
   offeredMulticastAddr PacketDataProtoAddr,
   accessPointName AccessPointName,
   --<iei format="tlv">35</iei>
   mbmsPCO MBMS-PCO OPTIONAL
}

/* 9.5.26 - GSM Request MBMS Context Activation Reject */

mt-RequestMBMSCtxtActRej INTEGER ::= 90

obj-RequestMBMSCtxtActRej NAS-PROTOCOL-CLASS ::= { 
   ID sessMgmt, mt-RequestMBMSCtxtActRej
   TYPE RequestMBMSCtxtActRej
}

RequestMBMSCtxtActRej ::= SEQUENCE {
   smCause SMCauseValue,
   --<iei format="tlv">35</iei>
   mbmsPCO MBMS-PCO OPTIONAL
}

END
